~/Desktop/LEP LSP/LEP-CONFIG.LSP:
    1: ;=====================================================================
    2: ;
    3: ;  ПРОЕКТ:      LEP (Автоматизация проектирования ЛЭП)
    4: ;
    5: ;  ФАЙЛ:        LEP-CONFIG.LSP
    6: ;
    7: ;  ВЕРСИЯ:      0.1
    8: ;
    9: ;  АВТОРЫ:      Пользователь + ChatGPT
   10: ;
   11: ;  НАЗНАЧЕНИЕ:
   12: ;
   13: ;  Данный файл содержит ВСЕ глобальные настройки проекта.
   14: ;
   15: ;  ВАЖНО!
   16: ;
   17: ;  Любые строки, числа, имена слоёв, размеры текста,
   18: ;  цвета, коэффициенты округления и прочие параметры
   19: ;  должны храниться ТОЛЬКО ЗДЕСЬ.
   20: ;
   21: ;  Остальные модули НЕ ДОЛЖНЫ содержать "магических"
   22: ;  чисел и строк.
   23: ;
   24: ;=====================================================================
   25: 
   26: 
   27: 
   28: ;=====================================================================
   29: ;                           ВЕРСИЯ ПРОЕКТА
   30: ;=====================================================================
   31: 
   32: (setq *LEP-Version* "0.1")
   33: 
   34: 
   35: 
   36: ;=====================================================================
   37: ;                           НАСТРОЙКИ ПРОЕКТА
   38: ;=====================================================================
   39: 
   40: (setq *LEP-ProjectName* "LEP")
   41: 
   42: 
   43: 
   44: ;=====================================================================
   45: ;                           СЛОИ
   46: ;=====================================================================
   47: 
   48: ;; Подложка
   49: 
   50: (setq *LEP-Layer-Kadastr*       "LEP-KADASTR")
   51: 
   52: 
   53: ;; Воздушные линии
   54: 
   55: (setq *LEP-Layer-Proj-VL*       "LEP-PROJ-VL")
   56: (setq *LEP-Layer-Exist-VL*      "LEP-EXIST-VL")
   57: 
   58: 
   59: ;; Кабельные линии
   60: 
   61: (setq *LEP-Layer-Proj-KL*       "LEP-PROJ-KL")
   62: (setq *LEP-Layer-Exist-KL*      "LEP-EXIST-KL")
   63: 
   64: 
   65: ;; Опоры
   66: 
   67: (setq *LEP-Layer-Proj-Pole*     "LEP-PROJ-POLES")
   68: (setq *LEP-Layer-Exist-Pole*    "LEP-EXIST-POLES")
   69: 
   70: 
   71: ;; Подстанции
   72: 
   73: (setq *LEP-Layer-Proj-MTP*      "LEP-PROJ-MTP")
   74: (setq *LEP-Layer-Proj-RLK*      "LEP-PROJ-RLK")
   75: (setq *LEP-Layer-Exist-TP*      "LEP-EXIST-TP")
   76: (setq *LEP-Layer-Proj-TP*       "LEP-PROJ-TP")
   77: 
   78: 
   79: ;; Текст
   80: 
   81: (setq *LEP-Layer-Text*          "LEP-TEXT")
   82: 
   83: 
   84: ;; Размеры
   85: 
   86: (setq *LEP-Layer-Dim*           "LEP-DIM")
   87: 
   88: 
   89: 
   90: ;=====================================================================
   91: ;                           ЦВЕТА СЛОЁВ
   92: ;=====================================================================
   93: ;
   94: ; Используются стандартные ACI цвета AutoCAD.
   95: ;
   96: ; При необходимости можно изменить здесь, не меняя код.
   97: ;
   98: ;=====================================================================
   99: 
  100: (setq *LEP-Color-Proj*          1)      ; Красный
  101: (setq *LEP-Color-Exist*         8)      ; Серый
  102: (setq *LEP-Color-Text*          7)      ; Белый
  103: (setq *LEP-Color-Dim*           2)      ; Желтый
  104: (setq *LEP-Color-Kadastr*       9)
  105: 
  106: 
  107: 
  108: ;=====================================================================
  109: ;                     ВЫСОТЫ ТЕКСТА
  110: ;=====================================================================
  111: 
  112: (setq *LEP-TextHeight*          2.5)
  113: 
  114: 
  115: 
  116: ;=====================================================================
  117: ;                  ОКРУГЛЕНИЕ ДЛИН
  118: ;=====================================================================
  119: ;
  120: ; Пока принято округлять до 5 метров.
  121: ;
  122: ; При необходимости изменить только здесь.
  123: ;
  124: ;=====================================================================
  125: 
  126: (setq *LEP-LengthRound*         5.0)
  127: 
  128: 
  129: 
  130: ;=====================================================================
  131: ;                НАСТРОЙКИ ПОДПИСЕЙ ПРОЛЁТОВ
  132: ;=====================================================================
  133: 
  134: (setq *LEP-SpanTextOffset*      3.0)
  135: 
  136: (setq *LEP-SpanTextRotation*    0)
  137: 
  138: 
  139: 
  140: ;=====================================================================
  141: ;                  ФАЙЛЫ СПРАВОЧНИКОВ
  142: ;=====================================================================
  143: 
  144: (setq *LEP-MaterialsFile* "materials.csv")
  145: 
  146: 
  147: 
  148: ;=====================================================================
  149: ;                      ИМЕНА БЛОКОВ
  150: ;=====================================================================
  151: 
  152: ;
  153: ; ВНИМАНИЕ!
  154: ;
  155: ; Пока здесь временные значения.
  156: ;
  157: ; После того как изучим библиотеку блоков,
  158: ; заменим их на реальные.
  159: ;
  160: ;
  161: 
  162: (setq *LEP-Block-Pole*          "POLE_DYNAMIC")
  163: (setq *LEP-Block-MTP*           "MTP160")
  164: (setq *LEP-Block-RLK*           "RLK")
  165: 
  166: 
  167: 
  168: ;=====================================================================
  169: ;                НАСТРОЙКИ КАЛИБРОВКИ
  170: ;=====================================================================
  171: 
  172: (setq *LEP-ReferenceLengths*
  173:       '(10.0 20.0 50.0 100.0))
  174: 
  175: ;=====================================================================
  176: ;                 СПИСОК ТИПОВ ОПОР
  177: ;
  178: ; Используется:
  179: ; - выбор пользователем;
  180: ; - подписи;
  181: ; - ведомость.
  182: ;
  183: ; Первый элемент:
  184: ; отображаемое название.
  185: ;
  186: ; Второй элемент:
  187: ; условный код для учета.
  188: ;
  189: ;=====================================================================
  190: 
  191: 
  192: (setq *LEP-PoleTypes*
  193: 
  194:     '(
  195: 
  196:         ("П23"       . "П23")
  197: 
  198:         ("УП23"      . "УП23")
  199: 
  200:         ("А23"       . "А23")
  201: 
  202:         ("УА23"      . "УА23")
  203: 
  204:         ("УП21"      . "УП21")
  205: 
  206:         ("К21"       . "К21")
  207: 
  208:         ("П20-3Н"    . "П20-3Н")
  209: 
  210:         ("А20-3Н"    . "А20-3Н")
  211: 
  212:         ("УА20-3Н"   . "УА20-3Н")
  213: 
  214:         ("УП20-3Н"   . "УП20-3Н")
  215: 
  216:     )
  217: 
  218: )
  219: 
  220: 
  221: ;=====================================================================
  222: ;                 СЛУЖЕБНЫЕ ПЕРЕМЕННЫЕ
  223: ;=====================================================================
  224: 
  225: (setq *LEP-CurrentRoute* nil)
  226: 
  227: (setq *LEP-CurrentScale* 1.0)
  228: 
  229: 
  230: 
  231: (princ
  232:   (strcat
  233:     "\n"
  234:     "=========================================\n"
  235:     " LEP CONFIG "
  236:     *LEP-Version*
  237:     " загружен.\n"
  238:     "========================================="
  239:   )
  240: )
  241: 
  242: (princ)
~/Desktop/LEP LSP/LEP-DATA.LSP:
    1: ;=====================================================================
    2: ;
    3: ;   ПРОЕКТ:
    4: ;   LEP
    5: ;
    6: ;   ФАЙЛ:
    7: ;   LEP-DATA.LSP
    8: ;
    9: ;   ВЕРСИЯ:
   10: ;   0.2
   11: ;
   12: ;   НАЗНАЧЕНИЕ:
   13: ;
   14: ;   Хранение данных объектов проекта LEP.
   15: ;
   16: ;   Каждый объект получает набор параметров:
   17: ;
   18: ;   ROUTE
   19: ;   TYPE
   20: ;   STATUS
   21: ;   MATERIAL
   22: ;   LENGTH
   23: ;   POWER
   24: ;
   25: ;   Данные сохраняются внутри DWG.
   26: ;
   27: ;=====================================================================
   28: 
   29: 
   30: 
   31: ;=====================================================================
   32: ;                       НАСТРОЙКИ
   33: ;=====================================================================
   34: 
   35: 
   36: (setq *LEP-RegApp*
   37: 
   38:     "LEP_DATA"
   39: 
   40: )
   41: 
   42: 
   43: 
   44: (if
   45: 
   46:     (not *LEP-RouteCounter*)
   47: 
   48:     (setq *LEP-RouteCounter* 1)
   49: 
   50: )
   51: 
   52: 
   53: 
   54: ;=====================================================================
   55: ;
   56: ; LEP:RegisterApp
   57: ;
   58: ; Регистрация приложения XDATA.
   59: ;
   60: ; AutoCAD требует регистрации имени.
   61: ;
   62: ;=====================================================================
   63: 
   64: 
   65: (defun LEP:RegisterApp (/)
   66: 
   67:     (if
   68: 
   69:         (not
   70: 
   71:             (tblsearch
   72: 
   73:                 "APPID"
   74: 
   75:                 *LEP-RegApp*
   76: 
   77:             )
   78: 
   79:         )
   80: 
   81:         (regapp
   82: 
   83:             *LEP-RegApp*
   84: 
   85:         )
   86: 
   87:     )
   88: 
   89: )
   90: 
   91: 
   92: 
   93: ;=====================================================================
   94: ;
   95: ; LEP:CreateRouteID
   96: ;
   97: ; Создание номера маршрута.
   98: ;
   99: ;=====================================================================
  101: 
  102: (defun LEP:CreateRouteID (/ ID)
  103: 
  104: 
  105:     (setq ID
  106: 
  107:         (strcat
  108: 
  109:             "LEP_ROUTE_"
  110: 
  111:             (substr
  112: 
  113:                 (strcat
  114: 
  115:                     "0000"
  116: 
  117:                     (itoa *LEP-RouteCounter*)
  118: 
  119:                 )
  120: 
  121:                 (-
  122: 
  123:                     (strlen
  124: 
  125:                         (strcat
  126: 
  127:                             "0000"
  128: 
  129:                             (itoa *LEP-RouteCounter*)
  130: 
  131:                         )
  132: 
  133:                     )
  134: 
  135:                     3
  136: 
  137:                 )
  138: 
  139:             )
  140: 
  141:         )
  142: 
  143:     )
  144: 
  145: 
  146:     (setq *LEP-RouteCounter*
  147: 
  148:         (1+
  149: 
  150:             *LEP-RouteCounter*
  151: 
  152:         )
  153: 
  154:     )
  155: 
  156: 
  157:     ID
  158: 
  159: )
  160: 
  161: 
  162: 
  163: ;=====================================================================
  164: ;
  165: ; LEP:SetData
  166: ;
  167: ; Записывает данные в объект.
  168: ;
  169: ; Формат входных данных:
  170: ;
  171: ; (
  172: ;  ("TYPE" . "POLE")
  173: ;  ("MODEL" . "П20-3Н")
  174: ;  ("STATUS" . "PROJECT")
  175: ; )
  176: ;
  177: ;=====================================================================
  178: 
  179: 
  180: (defun LEP:SetData
  181: 
  182:     (
  183: 
  184:         Ent
  185: 
  186:         DataList
  187: 
  188:         /
  189: 
  190:         OldData
  191: 
  192:         NewData
  193: 
  194:     )
  195: 
  196: 
  197:     (LEP:RegisterApp)
  198: 
  199: 
  200: 
  201:     (setq NewData
  202: 
  203:         (list
  204: 
  205:             (cons
  206: 
  207:                 1001
  208: 
  209:                 *LEP-RegApp*
  210: 
  211:             )
  212: 
  213:         )
  214: 
  215:     )
  216: 
  217: 
  218: 
  219:     (foreach Item DataList
  220: 
  221:         (setq NewData
  222: 
  223:             (append
  224: 
  225:                 NewData
  226: 
  227:                 (list
  228: 
  229:                     (cons
  230: 
  231:                         1000
  232: 
  233:                         (strcat
  234: 
  235:                             (car Item)
  236: 
  237:                             "="
  238: 
  239:                             (cdr Item)
  240: 
  241:                         )
  242: 
  243:                     )
  244: 
  245:                 )
  246: 
  247:             )
  248: 
  249:         )
  250: 
  251:     )
  252: 
  253: 
  254: 
  255:     (regapp *LEP-RegApp*)
  256: 
  257: 
  258: 
  259:     (entmod
  260: 
  261:         (append
  262: 
  263:             (entget Ent)
  264: 
  265:             NewData
  266: 
  267:         )
  268: 
  269:     )
  270: 
  271: 
  272: 
  273:     (entupd Ent)
  274: 
  275: 
  276: 
  277: )
  278: 
  279: 
  280: 
  281: ;=====================================================================
  282: ;
  283: ; LEP:GetData
  284: ;
  285: ; Читает данные объекта.
  286: ;
  287: ; Возвращает список.
  288: ;
  289: ;=====================================================================
  290: 
  291: 
  292: (defun LEP:GetData
  293: 
  294:     (
  295: 
  296:         Ent
  297: 
  298:         /
  299: 
  300:         Obj
  301: 
  302:         Result
  303: 
  304:         Item
  305: 
  306:     )
  307: 
  308: 
  309:     (setq Result nil)
  310: 
  311: 
  312: 
  313:     (foreach Item
  314: 
  315:         (entget Ent
  316: 
  317:             (list *LEP-RegApp*)
  318: 
  319:         )
  320: 
  321: 
  322:         (if
  323: 
  324:             (=
  325: 
  326:                 (car Item)
  327: 
  328:                 1000
  329: 
  330:             )
  331: 
  332:             (setq Result
  333: 
  334:                 (append
  335: 
  336:                     Result
  337: 
  338:                     (list
  339: 
  340:                         (cdr Item)
  341: 
  342:                     )
  343: 
  344:                 )
  345: 
  346:             )
  347: 
  348:         )
  349: 
  350:     )
  351: 
  352: 
  353:     Result
  354: 
  355: )
  356: 
  357: 
  358: 
  359: ;=====================================================================
  360: ;
  361: ; LEP:AddRoute
  362: ;
  363: ; Записывает маршрут.
  364: ;
  365: ;=====================================================================
  366: 
  367: 
  368: (defun LEP:AddRoute
  369: 
  370:     (
  371: 
  372:         Ent
  373: 
  374:         /
  375: 
  376:         ID
  377: 
  378:     )
  379: 
  380: 
  381:     (setq ID
  382: 
  383:         (LEP:CreateRouteID)
  384: 
  385:     )
  386: 
  387: 
  388:     (LEP:SetData
  389: 
  390:         Ent
  391: 
  392:         (list
  393: 
  394:             (cons
  395: 
  396:                 "TYPE"
  397: 
  398:                 "ROUTE"
  399: 
  400:             )
  401: 
  402:             (cons
  403: 
  404:                 "ID"
  405: 
  406:                 ID
  407: 
  408:             )
  409: 
  410:             (cons
  411: 
  412:                 "STATUS"
  413: 
  414:                 "PROJECT"
  415: 
  416:             )
  417: 
  418:         )
  419: 
  420:     )
  421: 
  422: 
  423:     ID
  424: 
  425: )
  426: 
  427: 
  428: 
  429: ;=====================================================================
  430: ;
  431: ; LEP:AddPoleData
  432: ;
  433: ; Запись данных опоры.
  434: ;
  435: ;=====================================================================
  436: 
  437: 
  438: (defun LEP:AddPoleData
  439: 
  440:     (
  441: 
  442:         Ent
  443: 
  444:         RouteID
  445: 
  446:         PoleType
  447: 
  448:     )
  449: 
  450: 
  451:     (LEP:SetData
  452: 
  453:         Ent
  454: 
  455:         (list
  456: 
  457:             (cons
  458: 
  459:                 "TYPE"
  460: 
  461:                 "POLE"
  462: 
  463:             )
  464: 
  465:             (cons
  466: 
  467:                 "ROUTE"
  468: 
  469:                 RouteID
  470: 
  471:             )
  472: 
  473:             (cons
  474: 
  475:                 "MODEL"
  476: 
  477:                 PoleType
  478: 
  479:             )
  480: 
  481:             (cons
  482: 
  483:                 "STATUS"
  484: 
  485:                 "PROJECT"
  486: 
  487:             )
  488: 
  489:         )
  490: 
  491:     )
  492: 
  493: 
  494: )
  495: 
  496: 
  497: 
  498: (princ "\nLEP-DATA v0.2 загружен.")
  499: 
  500: (princ)
~/Desktop/LEP LSP/LEP-POLE.LSP:
    1: ;=====================================================================
    2: ;
    3: ;   ПРОЕКТ:
    4: ;   LEP
    5: ;
    6: ;   ФАЙЛ:
    7: ;   LEP-POLE.LSP
    8: ;
    9: ;   ВЕРСИЯ:
   10: ;   0.1
   11: ;
   12: ;   НАЗНАЧЕНИЕ:
   13: ;
   14: ;   Автоматическая установка опор на вершины
   15: ;   проектируемого маршрута ЛЭП.
   16: ;
   17: ;=====================================================================
   18: 
   19: 
   20: 
   21: ;=====================================================================
   22: ;
   23: ; НАСТРОЙКИ
   24: ;
   25: ;=====================================================================
   26: 
   27: 
   28: ;; Временные имена вариантов опор.
   29: ;;
   30: ;; После подключения materials.csv
   31: ;; этот список будет заменен внешним файлом.
   32: 
   33: (setq *LEP-PoleTypes*
   34: 
   35:     '(
   36:         ("П20-3Н"  . "П20-3Н")
   37:         ("А20-3Н"  . "А20-3Н")
   38:         ("УА20-3Н" . "УА20-3Н")
   39:         ("А23"     . "А23")
   40:      )
   41: 
   42: )
   43: 
   44: 
   45: 
   46: ;=====================================================================
   47: ;
   48: ; LEP:GetPoleType
   49: ;
   50: ; Запрос типа опоры у пользователя.
   51: ;
   52: ; Возвращает имя блока.
   53: ;
   54: ;=====================================================================
   55: 
   56: 
   57: (defun LEP:GetPoleType (/ Choice)
   58: 
   59:     (initget "1 2 3 4")
   60: 
   61:     (setq Choice
   62: 
   63:         (getkword
   64: 
   65:             "\nВыберите опору [1-П20-3Н/2-А20-3Н/3-УА20-3Н/4-А23]: "
   66: 
   67:         )
   68: 
   69:     )
   70: 
   71: 
   72:     (cond
   73: 
   74:         ((= Choice "1")
   75:             "П20-3Н"
   76:         )
   77: 
   78:         ((= Choice "2")
   79:             "А20-3Н"
   80:         )
   81: 
   82:         ((= Choice "3")
   83:             "УА20-3Н"
   84:         )
   85: 
   86:         ((= Choice "4")
   87:             "А23"
   88:         )
   89: 
   90:     )
   91: 
   92: )
   93: 
   94: 
   95: 
   96: ;=====================================================================
   97: ;
   98: ; LEP:InsertPole
   99: ;
  100: ; Вставка блока опоры.
  101: ;
  102: ; Вход:
  103: ;
  104: ; Point - координата вершины
  105: ; BlockName - имя блока
  106: ;
  107: ;=====================================================================
  108: 
  109: 
  110: (defun LEP:InsertPole
  111: 
  112:     (
  113: 
  114:         Point
  115: 
  116:         BlockName
  117: 
  118:         /
  119: 
  120:         OldLayer
  121: 
  122:         Ent
  123: 
  124:     )
  125: 
  126: 
  127:     ;; Запоминаем слой
  128: 
  129:     (setq OldLayer
  130:         (getvar "CLAYER")
  131:     )
  132: 
  133: 
  134:     ;; Переключаемся на слой опор
  135: 
  136:     (LEP:SetCurrentLayer
  137:         *LEP-Layer-Proj-Pole*
  138:     )
  139: 
  140: 
  141:     ;; Вставка блока
  142: 
  143:     (command
  144: 
  145:         "_.-INSERT"
  146: 
  147:         BlockName
  148: 
  149:         Point
  150: 
  151:         1
  152: 
  153:         1
  154: 
  155:         0
  156: 
  157:     )
  158: 
  159: 
  160:     ;; Получаем последний объект
  161: 
  162:     (setq Ent
  163: 
  164:         (entlast)
  165: 
  166:     )
  167: 
  168: 
  169:     ;; Возвращаем слой
  170: 
  171:     (setvar
  172: 
  173:         "CLAYER"
  174: 
  175:         OldLayer
  176: 
  177:     )
  178: 
  179: 
  180:     Ent
  181: 
  182: )
  183: 
  184: 
  185: 
  186: ;=====================================================================
  187: ;
  188: ; LEP:PlacePolesOnRoute
  189: ;
  190: ; Основная функция установки опор.
  191: ;
  192: ;=====================================================================
  193: 
  194: 
  195: (defun LEP:PlacePolesOnRoute (RouteEnt / Vertices Point PoleType PoleEnt RouteData RouteID i)
  196:     ;; Читаем XDATA полилинии, чтобы получить её честный RouteID
  197:     ;; Извлекаем группу 1001 (LEP_DATA) и находим сохраненный ID
  198:     (setq RouteData (assoc -3 (entget RouteEnt '("LEP_DATA"))))
  199:     (if RouteData
  200:         (setq RouteID (cdr (nth 2 (car (cdr RouteData))))) ; Достаем сохраненный ID маршрута
  201:         (setq RouteID "LEP_ROUTE_UNKNOWN")
  202:     )
  203:     
  204:     (setq Vertices (LEP:GetVertices RouteEnt))
  205:     (setq i 0)
  206: 
  207:     (foreach Point Vertices
  208:         (princ (strcat "\nВершина №" (itoa (+ i 1))))
  209:         (setq PoleType (LEP:GetPoleType))
  210:         
  211:         (if PoleType
  212:             (progn
  213:                 ;; Вставляем блок
  214:                 (setq PoleEnt (LEP:InsertPole Point PoleType))
  215:                 (if PoleEnt
  216:                     (progn
  217:                         ;; Накладываем геометрическую зависимость совмещения.
  218:                         ;; Передаем координаты Point, чтобы AutoCAD Mac точно определил точку связывания
  219:                         (command "_.GEOMCONSTRAINT" "_COincident" PoleEnt Point RouteEnt Point "")
  220:                         
  221:                         ;; Записываем данные в базу чертежа
  222:                         (LEP:AddPoleData PoleEnt RouteID PoleType)
  223:                     )
  224:                 )
  225:             )
  226:         )
  227:         (setq i (+ i 1))
  228:     )
  229: )
  230: 
  231: (defun C:LEP-POLE (/ Route OldOs OldError)
  232:     (setq OldError *error*)
  233:     (defun *error* (msg)
  234:         (if OldOs (setvar "OSMODE" OldOs))
  235:         (setq *error* OldError)
  236:         (princ (strcat "\nКоманда прервана: " msg))
  237:         (princ)
  238:     )
  239: 
  240:     (LEP:PrintHeader "Установка опор")
  241:     (setq Route (car (entsel "\nВыберите полилинию маршрута: ")))
  242: 
  243:     (if Route
  244:         (progn
  245:             (setq OldOs (getvar "OSMODE"))
  246:             (setvar "OSMODE" 0)
  247: 
  248:             (LEP:PlacePolesOnRoute Route)
  249: 
  250:             (setvar "OSMODE" OldOs)
  251:         )
  252:         (princ "\nМаршрут не выбран.")
  253:     )
  254:     (setq *error* OldError)
  255:     (LEP:PrintFooter)
  256:     (princ)
  257: )
  258: 
  259: 
  260: 
  261: ;=====================================================================
  262: ;
  263: ; ОСНОВНАЯ КОМАНДА
  264: ;
  265: ;=====================================================================
  266: 
  267: 
  268: ;=====================================================================
  269: ; ОСНОВНАЯ КОМАНДА (С защитой привязок OSMODE)
  270: ;=====================================================================
  271: (defun C:LEP-POLE (/ Route OldOs OldError)
  272: 
  273:     ;; Локальный обработчик ошибок (если нажат ESC)
  274:     (setq OldError *error*)
  275:     (defun *error* (msg)
  276:         (if OldOs (setvar "OSMODE" OldOs)) ; Возвращаем привязки
  277:         (setq *error* OldError)
  278:         (princ (strcat "\nКоманда прервана: " msg))
  279:         (princ)
  280:     )
  281: 
  282:     (LEP:PrintHeader "Установка опор")
  283:     
  284:     (setq Route (car (entsel "\nВыберите полилинию маршрута: ")))
  285: 
  286:     (if Route
  287:         (progn
  288:             ;; Запоминаем текущие привязки и отключаем их (0 = выкл)
  289:             (setq OldOs (getvar "OSMODE"))
  290:             (setvar "OSMODE" 0)
  291: 
  292:             ;; Запуск твоего пошагового выбора опор
  293:             (LEP:PlacePolesOnRoute Route)
  294: 
  295:             ;; Возвращаем исходные привязки после успешного завершения
  296:             (setvar "OSMODE" OldOs)
  297:         )
  298:         (princ "\nМаршрут не выбран.")
  299:     )
  300:     
  301:     ;; Восстанавливаем штатный обработчик ошибок
  302:     (setq *error* OldError)
  303:     (LEP:PrintFooter)
  304:     (princ)
  305: )
  306: 
  307: 
  308: 
  309: (princ "\nLEP-POLE загружен.")
  310: 
  311: (princ)
~/Desktop/LEP LSP/LEP-POLYLINE.LSP:
    1: ;=====================================================================
    2: ;
    3: ;   ПРОЕКТ:
    4: ;   LEP
    5: ;
    6: ;   ФАЙЛ:
    7: ;   LEP-POLYLINE.LSP
    8: ;
    9: ;   Работа с полилиниями.
   10: ;
   11: ;=====================================================================
   12: 
   13: 
   14: 
   15: ;=====================================================================
   16: ;
   17: ; LEP:GetVertices
   18: ;
   19: ; Возвращает список всех вершин LWPOLYLINE.
   20: ;
   21: ; Вход:
   22: ;
   23: ; ename
   24: ;
   25: ; Выход:
   26: ;
   27: ; (
   28: ;   (x y z)
   29: ;   (x y z)
   30: ;   ...
   31: ; )
   32: ;
   33: ;=====================================================================
   34: 
   35: (defun LEP:GetVertices (Ent / Data Result Item)
   36: 
   37:     (setq Data (entget Ent))
   38: 
   39:     (setq Result nil)
   40: 
   41:     (foreach Item Data
   42: 
   43:         (if (= (car Item) 10)
   44: 
   45:             (setq Result
   46: 
   47:                 (append
   48: 
   49:                     Result
   50: 
   51:                     (list
   52: 
   53:                         (cdr Item)
   54: 
   55:                     )
   56: 
   57:                 )
   58: 
   59:             )
   60: 
   61:         )
   62: 
   63:     )
   64: 
   65:     Result
   66: 
   67: )
   68: 
   69: 
   70: 
   71: ;=====================================================================
   72: ;
   73: ; LEP:GetVertexCount
   74: ;
   75: ;=====================================================================
   76: 
   77: (defun LEP:GetVertexCount (Ent)
   78: 
   79:     (length
   80: 
   81:         (LEP:GetVertices Ent)
   82: 
   83:     )
   84: 
   85: )
   86: 
   87: 
   88: 
   89: ;=====================================================================
   90: ;
   91: ; LEP:GetSegmentLength
   92: ;
   93: ; Возвращает длину между двумя соседними вершинами.
   94: ;
   95: ;=====================================================================
   96: 
   97: (defun LEP:GetSegmentLength
   98: 
   99: (
  100: 
  101: Ent
  102: 
  103: Index
  104: 
  105: /
  106: 
  107: Vertices
  108: 
  109: P1
  110: 
  111: P2
  112: 
  113: )
  114: 
  115:     (setq Vertices
  116: 
  117:         (LEP:GetVertices Ent)
  118: 
  119:     )
  120: 
  121:     (setq P1
  122: 
  123:         (nth Index Vertices)
  124: 
  125:     )
  126: 
  127:     (setq P2
  128: 
  129:         (nth
  130: 
  131:             (+ Index 1)
  132: 
  133:             Vertices
  134: 
  135:         )
  136: 
  137:     )
  138: 
  139:     (distance P1 P2)
  140: 
  141: )
  142: 
  143: 
  144: 
  145: ;=====================================================================
  146: ;
  147: ; LEP:GetSegmentList
  148: ;
  149: ; Возвращает список длин всех пролетов.
  150: ;
  151: ;=====================================================================
  152: 
  153: (defun LEP:GetSegmentList
  154: 
  155: (
  156: 
  157: Ent
  158: 
  159: /
  160: 
  161: Vertices
  162: 
  163: Result
  164: 
  165: i
  166: 
  167: )
  168: 
  169:     (setq Vertices
  170: 
  171:         (LEP:GetVertices Ent)
  172: 
  173:     )
  174: 
  175:     (setq Result nil)
  176: 
  177:     (setq i 0)
  178: 
  179:     (repeat
  180: 
  181:         (- (length Vertices) 1)
  182: 
  183:         (setq Result
  184: 
  185:             (append
  186: 
  187:                 Result
  188: 
  189:                 (list
  190: 
  191:                     (distance
  192: 
  193:                         (nth i Vertices)
  194: 
  195:                         (nth (+ i 1) Vertices)
  196: 
  197:                     )
  198: 
  199:                 )
  200: 
  201:             )
  202: 
  203:         )
  204: 
  205:         (setq i (1+ i))
  206: 
  207:     )
  208: 
  209:     Result
  210: 
  211: )
  212: 
  213: 
  214: 
  215: (princ "\nLEP-POLYLINE загружен.")
  216: 
  217: (princ)
~/Desktop/LEP LSP/LEP-REPORT.LSP:
    1: ;=====================================================================
    2: ; ПРОЕКТ:       LEP (Автоматизация проектирования ЛЭП)
    3: ; ФАЙЛ:         LEP-REPORT.LSP
    4: ; ВЕРСИЯ:       0.4
    5: ; НАЗНАЧЕНИЕ:   Полностью автоматический сбор объемов материалов 
    6: ;               (чистые длины линий без округления и штучные опоры) 
    7: ;               с разделением по ID трасс и экспортом в формат CSV.
    8: ;=====================================================================
    9: 
   10: (defun C:LEP-REPORT ( /  ; Список локальных переменных для защиты памяти
   11:                         VL-SS KL-SS PoleSS CsvPath CsvFile i Ent VlaObj 
   12:                         Len Layer Name XData ResID PoleList Item 
   13:                         MasterList RouteID FoundRoute FoundPole 
   14:                         FileCheck )
   15:     
   16:     ; Подключаем базовые функции Visual LISP (ActiveX) для расширенной работы с объектами
   17:     (vl-load-com)
   18:     
   19:     ; Выводим стандартное текстовое приветствие из LEP-UTILS
   20:     (LEP:PrintHeader "Автоматическая выгрузка ведомости в CSV")
   21: 
   22:     ;-----------------------------------------------------------------
   23:     ; СТРУКТУРА ДАННЫХ (MasterList):
   24:     ; Хранит агрегированные данные в виде вложенных списков по каждой трассе:
   25:     ; (
   26:     ;   ("LEP_ROUTE_1" . ( ("LineLen" . 145.62) ("П20-3Н" . 4) ("А23" . 1) ))
   27:     ;   ("LEP_ROUTE_2" . ( ("LineLen" . 89.11)  ("П23" . 3) ))
   28:     ; )
   29:     ;-----------------------------------------------------------------
   30:     (setq MasterList nil)
   31: 
   32:     ;=================================================================
   33:     ; ЭТАП 1: СБОР И ГЕОМЕТРИЧЕСКИЙ РАСЧЕТ ЛИНЕЙНОЙ ЧАСТИ (ВЛ и КЛ)
   34:     ;=================================================================
   35:     
   36:     ; Формируем выборку всех легких полилиний (LWPOLYLINE) на проектных слоях ВЛ и КЛ
   37:     (setq VL-SS (ssget "_X" (list '(0 . "LWPOLYLINE") 
   38:                                   (cons 8 (strcat *LEP-Layer-Proj-VL* "," *LEP-Layer-Proj-KL*)))))
   39: 
   40:     (if VL-SS
   41:         (progn
   42:             (setq i 0)
   43:             ; Цикл перебора всех найденных кабелей и проводов
   44:             (repeat (sslength VL-SS)
   45:                 (setq Ent (ssname VL-SS i))
   46:                 ; Преобразуем стандартный ename во вла-объект для доступа к ActiveX методам
   47:                 (setq VlaObj (vlax-ename->vla-object Ent))
   48:                 
   49:                 ; Извлекаем чистую геометрическую длину объекта (БЕЗ ОКРУГЛЕНИЙ)
   50:                 (setq Len (vla-get-length VlaObj))
   51:                 
   52:                 ; Читаем расширенные данные (XDATA) объекта, привязанные к приложению "LEP_DATA"
   53:                 (setq XData (assoc -3 (entget Ent '("LEP_DATA"))))
   54:                 
   55:                 (if XData
   56:                     ; Если XDATA есть, вытаскиваем сохраненный уникальный ID трассы
   57:                     (setq RouteID (cdr (nth 4 (car (cdr XData)))))
   58:                     ; Если объект лежит на слое, но не размечен кодом — маркируем как потерянный
   59:                     (setq RouteID "НЕРАЗМЕЧЕННЫЕ_ЛИНИИ")
   60:                 )
   61: 
   62:                 ; Ищем, создана ли уже запись для этой трассы в нашем главном списке MasterList
   63:                 (setq FoundRoute (assoc RouteID MasterList))
   64:                 
   65:                 (if FoundRoute
   66:                     ; Если трасса уже есть, извлекаем её текущую длину, прибавляем новую и обновляем список
   67:                     (progn
   68:                         (setq PoleList (cdr FoundRoute))
   69:                         (setq FoundPole (assoc "LineLen" PoleList))
   70:                         (if FoundPole
   71:                             (setq PoleList (subst (cons "LineLen" (+ (cdr FoundPole) Len)) FoundPole PoleList))
   72:                             (setq PoleList (append PoleList (list (cons "LineLen" Len))))
   73:                         )
   74:                         (setq MasterList (subst (cons RouteID PoleList) FoundRoute MasterList))
   75:                     )
   76:                     ; Если трасса встретилась впервые, инициализируем её структуру с начальной длиной
   77:                     (setq MasterList (append MasterList (list (cons RouteID (list (cons "LineLen" Len))))))
   78:                 )
   79:                 (setq i (1+ i))
   80:             )
   81:         )
   82:     )
   83: 
   84:     ;=================================================================
   85:     ; ЭТАП 2: СБОР И АНАЛИЗ ПРОЕКТНЫХ ОПОР (ВКЛЮЧАЯ ДИНАМИЧЕСКИЕ БЛОКИ)
   86:     ;=================================================================
   87:     
   88:     ; Находим абсолютно все вхождения блоков (INSERT) на проектном слое опор
   89:     (setq PoleSS (ssget "_X" (list '(0 . "INSERT") (cons 8 *LEP-Layer-Proj-Pole*))))
   90: 
   91:     (if PoleSS
   92:         (progn
   93:             (setq i 0)
   94:             ; Поштучно перебираем все опоры на чертеже
   95:             (repeat (sslength PoleSS)
   96:                 (setq Ent (ssname PoleSS i))
   97:                 (setq VlaObj (vlax-ename->vla-object Ent))
   98:                 
   99:                 ; РЕШЕНИЕ ПРОБЛЕМЫ ДИНАМИЧЕСКИХ БЛОКОВ:
  100:                 ; vla-get-EffectiveName извлекает ИСХОДНОЕ имя блока из описания, 
  101:                 ; даже если на чертеже конкретный блок стал анонимным (*U...) из-за смены свойств видимости.
  102:                 (setq PoleName (vla-get-EffectiveName VlaObj))
  103:                 
  104:                 ; Считываем XDATA опоры для определения её принадлежности к конкретной линии
  105:                 (setq XData (assoc -3 (entget Ent '("LEP_DATA"))))
  106:                 
  107:                 (if XData
  108:                     (setq RouteID (cdr (nth 4 (car (cdr XData)))))
  109:                     (setq RouteID "ОПОРА_БЕЗ_ТРАССЫ")
  110:                 )
  111: 
  112:                 ; Проверяем наличие этой трассы в MasterList
  113:                 (setq FoundRoute (assoc RouteID MasterList))
  114:                 
  115:                 (if FoundRoute
  116:                     ; Если ветка трассы создана (например, на этапе обсчета линий)
  117:                     (progn
  118:                         (setq PoleList (cdr FoundRoute))
  119:                         ; Ищем конкретный тип опоры (например, "П20-3Н") внутри этой трассы
  120:                         (setq FoundPole (assoc PoleName PoleList))
  121:                         
  122:                         (if FoundPole
  123:                             ; Если тип опоры уже встречался на этой линии — инкрементируем счетчик (+1)
  124:                             (setq PoleList (subst (cons PoleName (1+ (cdr FoundPole))) FoundPole PoleList))
  125:                             ; Если тип опоры на этой линии новый — добавляем со значением 1
  126:                             (setq PoleList (append PoleList (list (cons PoleName 1))))
  127:                         )
  128:                         ; Записываем обновленный подсписок материалов обратно в главную базу данных трассы
  129:                         (setq MasterList (subst (cons RouteID PoleList) FoundRoute MasterList))
  130:                     )
  131:                     ; Если опора стоит изолированно и трассы еще не было в списке — создаем новую ветку
  132:                     (setq MasterList (append MasterList (list (cons RouteID (list (cons PoleName 1))))))
  133:                 )
  134:                 (setq i (1+ i))
  135:             )
  136:         )
  137:     )
  138: 
  139:     ;=================================================================
  140:     ; ЭТАП 3: АВТОМАТИЧЕСКАЯ ЗАПИСЬ ДАННЫХ В ФАЙЛ CSV С ЗАЩИТОЙ ОТ СБОЕВ
  141:     ;=================================================================
  142:     
  143:     ; Автоматически вычисляем путь к целевому CSV файлу в директории текущего DWG
  144:     (setq CsvPath (strcat (getvar "DWGPREFIX") (vl-filename-base (getvar "DWGNAME")) "_ведомость.csv"))
  145:     
  146:     ; ЗАЩИТА ОТ БЛОКИРОВКИ EXCEL:
  147:     ; Пробуем открыть файл в режиме добавления ("a"). Если Excel держит файл, open вернет nil.
  148:     (setq FileCheck (open CsvPath "a"))
  149:     
  150:     (if (not FileCheck)
  151:         ; Если файл заблокирован, прерываем выполнение и выводим громкое предупреждение
  152:         (progn
  153:             (princ "\n!!!!!!!!!!!!!!!!!!!!!!!!!!!!!!!!!!!!!!!!!!!!!!!!!!!!!!!!!!!!!!!")
  154:             (princ (strcat "\n[КРИТИЧЕСКАЯ ОШИБКА]: Файл ведомости заблокирован!"))
  155:             (princ "\nВозможно, этот CSV файл сейчас открыт в Microsoft Excel.")
  156:             (princ "\nПожалуйста, закройте Excel и запустите команду LEP-REPORT снова.")
  157:             (princ "\n!!!!!!!!!!!!!!!!!!!!!!!!!!!!!!!!!!!!!!!!!!!!!!!!!!!!!!!!!!!!!!!")
  158:         )
  159:         (progn
  160:             (close FileCheck) ; Закрываем проверочный дескриптор
  161:             
  162:             ; Открываем файл заново в режиме чистой перезаписи ("w")
  163:             (setq CsvFile (open CsvPath "w"))
  164:             
  165:             ; Записываем стандартную шапку таблицы. 
  166:             ; Разделитель — СТРОГО СЕМИКОЛОН (точка с запятой) для моментального открытия в русском Excel.
  167:             (write-line "Трасса;Наименование материала / оборудования;Количество;Ед. изм." CsvFile)
  168:             
  169:             ; Перебираем сформированную базу данных по всем трассам чертежа
  170:             (foreach RouteItem MasterList
  171:                 (setq ResID (car RouteItem))     ; ID текущей трассы
  172:                 (setq PoleList (cdr RouteItem))   ; Список её элементов
  173:                 
  174:                 ; Сначала выгружаем общую чистую длину кабельных/воздушных трасс
  175:                 (setq FoundPole (assoc "LineLen" PoleList))
  176:                 (if FoundPole
  177:                     (progn
  178:                         ; Для красоты определяем тип проводника по названию ID или слою.
  179:                         ; Выводим REAL-значение длины с точностью до 2 знаков после запятой без искажения округлением
  180:                         (write-line (strcat ResID ";Проводник (проектная длина согласно геометрии);" (rtos (cdr FoundPole) 2 2) ";м.") CsvFile)
  181:                     )
  182:                 )
  183:                 
  184:                 ; Теперь выгружаем все опоры, которые жестко привязаны к этой конкретной трассе
  185:                 (foreach Item PoleList
  186:                     (if (/= (car Item) "LineLen") ; Пропускаем системную переменную длины
  187:                         (write-line (strcat ResID ";Опора проектная типа " (car Item) ";" (itoa (cdr Item)) ";шт.") CsvFile)
  188:                     )
  189:                 )
  190:             )
  191:             
  192:             ; Закрываем файл, освобождая буфер обмена операционной системы
  193:             (close CsvFile)
  194:             
  195:             (princ "\n=======================================================")
  196:             (princ "\n[УСПЕХ] Сквозной сбор объемов завершен без ручного выбора.")
  197:             (princ (strcat "\n Файл сохранен: " CsvPath))
  198:             (princ "\n Данные сгруппированы по ID трасс на основе XDATA.")
  199:             (princ "\n Длины взяты в чистом виде без повторных округлений.")
  200:             (princ "\n=======================================================")
  201:         )
  202:     )
  203:     (LEP:PrintFooter)
  204:     (princ)
  205: )
  206: 
  207: (princ "\nМодуль LEP-REPORT v0.4 успешно интегрирован.")
  208: (princ)
~/Desktop/LEP LSP/LEP-ROUTE.LSP:
    1: ;=====================================================================
    2: ;
    3: ;   ПРОЕКТ:
    4: ;   LEP
    5: ;
    6: ;   ФАЙЛ:
    7: ;   LEP-ROUTE.LSP
    8: ;
    9: ;   ВЕРСИЯ:
   10: ;   0.2
   11: ;
   12: ;   НАЗНАЧЕНИЕ:
   13: ;
   14: ;   Создание маршрута проектируемой линии.
   15: ;
   16: ;   Алгоритм:
   17: ;
   18: ;   1. Пользователь рисует трассу PLINE.
   19: ;   2. Программа присваивает ей уникальный ID.
   20: ;   3. ID записывается внутрь DWG.
   21: ;   4. Далее к этому маршруту будут привязаны:
   22: ;
   23: ;      - опоры;
   24: ;      - пролеты;
   25: ;      - кабели;
   26: ;      - оборудование.
   27: ;
   28: ;=====================================================================
   29: 
   30: 
   31: 
   32: ;=====================================================================
   33: ;
   34: ; КОМАНДА:
   35: ;
   36: ; LEP-ROUTE
   37: ;
   38: ;=====================================================================
   39: 
   40: 
   41: (defun C:LEP-ROUTE
   42: 
   43:     (
   44: 
   45:         /
   46: 
   47:         OldLayer
   48: 
   49:         RouteEnt
   50: 
   51:         RouteID
   52: 
   53:     )
   54: 
   55: 
   56: 
   57:     (LEP:PrintHeader
   58: 
   59:         "Создание маршрута ЛЭП"
   60: 
   61:     )
   62: 
   63: 
   64: 
   65:     ;---------------------------------------------------------------
   66:     ; Запоминаем текущий слой
   67:     ;---------------------------------------------------------------
   68: 
   69:     (setq OldLayer
   70: 
   71:         (getvar "CLAYER")
   72: 
   73:     )
   74: 
   75: 
   76: 
   77:     ;---------------------------------------------------------------
   78:     ; Переключаемся на слой проектируемой ВЛ
   79:     ;---------------------------------------------------------------
   80: 
   81:     (LEP:SetCurrentLayer
   82: 
   83:         *LEP-Layer-Proj-VL*
   84: 
   85:     )
   86: 
   87: 
   88: 
   89:     (princ
   90: 
   91:         "\nУкажите точки трассы."
   92: 
   93:     )
   94: 
   95: 
   96: 
   97:     (princ
   98: 
   99:         "\nПосле завершения нажмите Enter."
  100: 
  101:     )
  102: 
  103: 
  104: 
  105:     ;---------------------------------------------------------------
  106:     ; Создание полилинии
  107:     ;---------------------------------------------------------------
  108: 
  109:     (LEP:SetCurrentLayer *LEP-Layer-Proj-VL*)
  110:     (princ "\nРисуйте трассу ЛЭП. После завершения нажмите Enter.")
  111:     
  112:     (command "_.PLINE")
  113:     ;; Цикл ожидания, пока пользователь не завершит команду PLINE
  114:     (while (> (getvar "CMDACTIVE") 0)
  115:         (command pause)
  116:     )
  117: 
  118:     ;; Теперь это гарантированно наша новая полилиния трассы
  119:     (setq RouteEnt (entlast))
  120: 
  121: 
  122: 
  123:     ;---------------------------------------------------------------
  124:     ; Проверка результата
  125:     ;---------------------------------------------------------------
  126: 
  127:     (if RouteEnt
  128: 
  129: 
  130:         (progn
  131: 
  132: 
  133: 
  134:             ;-------------------------------------------------------
  135:             ; Создаем ID маршрута
  136:             ;-------------------------------------------------------
  137: 
  138:             (setq RouteID
  139: 
  140:                 (LEP:AddRoute
  141: 
  142:                     RouteEnt
  143: 
  144:                 )
  145: 
  146:             )
  147: 
  148: 
  149: 
  150:             (princ
  151: 
  152:                 "\nСоздан маршрут: "
  153: 
  154:             )
  155: 
  156: 
  157:             (princ RouteID)
  158: 
  159: 
  160: 
  161:             ;-------------------------------------------------------
  162:             ; Сохраняем текущий маршрут
  163:             ;-------------------------------------------------------
  164: 
  165:             (setq *LEP-CurrentRoute*
  166: 
  167:                 RouteEnt
  168: 
  169:             )
  170: 
  171: 
  172: 
  173:         )
  174: 
  175: 
  176:         (princ
  177: 
  178:             "\nМаршрут не создан."
  179: 
  180:         )
  181: 
  182: 
  183:     )
  184: 
  185: 
  186: 
  187:     ;---------------------------------------------------------------
  188:     ; Возвращаем исходный слой
  189:     ;---------------------------------------------------------------
  190: 
  191:     (setvar
  192: 
  193:         "CLAYER"
  194: 
  195:         OldLayer
  196: 
  197:     )
  198: 
  199: 
  200: 
  201:     (LEP:PrintFooter)
  202: 
  203: 
  204: 
  205:     (princ)
  206: 
  207: )
  208: 
  209: 
  210: 
  211: (princ "\nLEP-ROUTE v0.2 загружен.")
  212: 
  213: (princ)
~/Desktop/LEP LSP/LEP-SCALE.LSP:
    1: ;=====================================================================
    2: ; ПРОЕКТ:       LEP (Автоматизация проектирования ЛЭП)
    3: ; ФАЙЛ:         LEP-SCALE.LSP
    4: ; ВЕРСИЯ:       0.2
    5: ; НАЗНАЧЕНИЕ:   Калибровка растровой подложки (скана, карты, кадастра).
    6: ;               Приводит чертеж к масштабу 1 единица = 1 метр 
    7: ;               на основе графической масштабной линейки.
    8: ;=====================================================================
    9: 
   10: (defun C:LEP-SCALE ( / ImgEnt P1 P2 MeasDist InputVal RealDist OldOs OldError )
   11: 
   12:     ;-----------------------------------------------------------------
   13:     ; ЛОКАЛЬНЫЙ ОБРАБОТЧИК ОШИБОК
   14:     ; Предотвращает поломку настроек AutoCAD при аварийном нажатии ESC
   15:     ;-----------------------------------------------------------------
   16:     (setq OldError *error*) ; Запоминаем стандартный обработчик ошибок
   17:     (defun *error* (msg)
   18:         (if OldOs (setvar "OSMODE" OldOs)) ; Гарантированно возвращаем привязки
   19:         (setq *error* OldError)            ; Восстанавливаем обработчик
   20:         (princ (strcat "\n[LEP-SCALE] Команда прервана: " msg))
   21:         (princ)
   22:     )
   23: 
   24:     ; Выводим фирменную шапку проекта из LEP-UTILS
   25:     (LEP:PrintHeader "Калибровка масштаба подложки")
   26:     
   27:     ;-----------------------------------------------------------------
   28:     ; ШАГ 1: ВЫБОР ОБЪЕКТА ПОДЛОЖКИ
   29:     ;-----------------------------------------------------------------
   30:     ; entsel приостанавливает выполнение и ждет клика по объекту.
   31:     ; Возвращает список: (ename (координаты клика)). Нам нужен только ename -> car.
   32:     (setq ImgEnt (car (entsel "\nВыберите изображение подложки (карту/кадастр): ")))
   33:     
   34:     (if ImgEnt
   35:         (progn
   36:             ; Временная деактивация объектных привязок (OSMODE = 0).
   37:             ; Это критично: при клике по картинке курсор не должен магнититься 
   38:             ; к случайным векторам геометрии, лежащим рядом.
   39:             (setq OldOs (getvar "OSMODE"))
   40:             (setvar "OSMODE" 0)
   41: 
   42:             ;---------------------------------------------------------
   43:             ; ШАГ 2: ФИКСАЦИЯ ОПОРНЫХ ТОЧЕК НА КАРТЕ
   44:             ;---------------------------------------------------------
   45:             ; getpoint запрашивает координаты. Передача точки P1 во второй вызов
   46:             ; включает "резиновый канат" (визуальную линию связи) от P1 к курсору.
   47:             (setq P1 (getpoint "\nУкажите ПЕРВУЮ точку на масштабной линейке карты: "))
   48:             (setq P2 (getpoint P1 "\nУкажите ВТОРУЮ точку на масштабной линейке карты: "))
   49:             
   50:             ; Возвращаем привязки инженеру сразу после сбора графических данных
   51:             (setvar "OSMODE" OldOs)
   52:             (setq OldOs nil) ; Обнуляем переменную, чтобы *error* её не трогал
   53: 
   54:             ; Вычисляем текущее расстояние в абстрактных единицах AutoCAD
   55:             (setq MeasDist (distance P1 P2))
   56:             (princ (strcat "\nИзмеренная длина в чертеже: " (rtos MeasDist 2 4) " ед."))
   57:             
   58:             ;---------------------------------------------------------
   59:             ; ШАГ 3: ИНТЕРАКТИВНЫЙ ЗАПРОС РЕАЛЬНОЙ ДЛИНЫ
   60:             ;---------------------------------------------------------
   61:             ; Механика initget + getreal:
   62:             ; Строка "10 20 50 100" задает жесткие макросы-ключи для быстрого ввода.
   63:             ; Если инженер введет одно из этих чисел или выберет в контекстном меню,
   64:             ; getreal вернет это значение как СТРОКУ (например, "50").
   65:             ; Если инженер введет ЛЮБОЕ ДРУГОЕ число (например, 25), getreal
   66:             ; поймет, что это свободный ввод, и вернет ЧИСЛО типа REAL (25.0).
   67:             (initget "10 20 50 100")
   68:             (setq InputVal (getreal "\nВведите реальное расстояние в метрах [10/20/50/100] или укажите своё: "))
   69:             
   70:             ; Анализируем тип возвращенного значения для предотвращения сбоя типизации
   71:             (cond
   72:                 ; Вариант А: Пользователь выбрал ключ из initget -> пришла строка
   73:                 ((= (type InputVal) 'STR)
   74:                     (setq RealDist (atof InputVal)) ; Парсим строку в вещественное число
   75:                 )
   76:                 ; Вариант Б: Пользователь ввел свое уникальное число -> пришло число
   77:                 ((= (type InputVal) 'REAL)
   78:                     (setq RealDist InputVal)
   79:                 )
   80:                 ; Вариант В: Пользователь нажал Enter без ввода (отмена)
   81:                 (t (setq RealDist nil))
   82:             )
   83:             
   84:             ;---------------------------------------------------------
   85:             ; ШАГ 4: МАТЕМАТИЧЕСКОЕ МАСШТАБИРОВАНИЕ ОБЪЕКТА
   86:             ;---------------------------------------------------------
   87:             ; Проверяем валидность полученного значения
   88:             (if (and RealDist (> RealDist 0.0))
   89:                 (progn
   90:                     ; Вызов встроенной команды SCALE через командный интерфейс AutoCAD.
   91:                     ; Механика Опции Ссылка (_Reference):
   92:                     ; Исходная длина (MeasDist) заменяется Новой длиной (RealDist).
   93:                     ; Использование префиксов "_." и "_" гарантирует корректный запуск
   94:                     ; команды на любых языковых версиях AutoCAD и на macOS.
   95:                     (command "_.SCALE" 
   96:                              ImgEnt             ; Выбираем наш объект
   97:                              ""                 ; Нажимаем Enter для завершения выбора объектов
   98:                              P1                 ; Базовая точка масштабирования (останется на месте)
   99:                              "_Reference"       ; Включаем режим масштабирования по ссылке
  100:                              MeasDist           ; Передаем старый размер
  101:                              RealDist           ; Передаем новый целевой размер в метрах
  102:                     )
  103:                     
  104:                     ; Печать лога калибровки для инженерного контроля
  105:                     (princ "\n==========================================")
  106:                     (princ (strcat "\n[УСПЕХ] Масштаб подложки откалиброван."))
  107:                     (princ (strcat "\n Пропорция: " (rtos MeasDist 2 2) " ед. -> превращены в " (rtos RealDist 2 2) " м."))
  108:                     (princ "\n Теперь 1 единица чертежа строго равна 1 метру.")
  109:                     (princ "\n==========================================")
  110:                 )
  111:                 (princ "\n[ОТМЕНА] Калибровка не выполнена: некорректное расстояние.")
  112:             )
  113:         )
  114:         (princ "\n[ОШИБКА] Объект подложки не выбран.")
  115:     )
  116:     
  117:     ; Восстанавливаем стандартную систему обработки ошибок AutoCAD
  118:     (setq *error* OldError)
  119:     (LEP:PrintFooter)
  120:     (princ)
  121: )
  122: 
  123: ;; Информируем консоль о штатной загрузке модуля
  124: (princ "\nМодуль LEP-SCALE v0.2 успешно загружен.")
  125: (princ)
~/Desktop/LEP LSP/LEP-SETUP.LSP:
    1: ;=====================================================================
    2: ;
    3: ;   ПРОЕКТ:
    4: ;   LEP
    5: ;
    6: ;   ФАЙЛ:
    7: ;   LEP-SETUP.LSP
    8: ;
    9: ;   ВЕРСИЯ:
   10: ;   0.1
   11: ;
   12: ;   НАЗНАЧЕНИЕ:
   13: ;
   14: ;   Подготавливает чертёж к работе.
   15: ;
   16: ;   Создаёт все необходимые слои проекта.
   17: ;
   18: ;   Если слой уже существует —
   19: ;   повторно он не создаётся.
   20: ;
   21: ;   После завершения выводится краткий отчёт.
   22: ;
   23: ;=====================================================================
   24: 
   25: 
   26: 
   27: ;=====================================================================
   28: ;                       СЛУЖЕБНАЯ ФУНКЦИЯ
   29: ;=====================================================================
   30: ;
   31: ; Создание слоя.
   32: ;
   33: ; Если слой уже существует —
   34: ; функция ничего не делает.
   35: ;
   36: ;=====================================================================
   37: 
   38: (defun LEP:CreateLayer (LayerName LayerColor /)
   39: 
   40:     (if (not (tblsearch "LAYER" LayerName))
   41: 
   42:         (progn
   43: 
   44:             (command
   45:                 "_.LAYER"
   46: 
   47:                 "_Make"
   48:                 LayerName
   49: 
   50:                 "_Color"
   51:                 LayerColor
   52:                 LayerName
   53: 
   54:                 ""
   55: 
   56:             )
   57: 
   58:             (princ
   59:                 (strcat
   60:                     "\nСоздан слой: "
   61:                     LayerName
   62:                 )
   63:             )
   64: 
   65:         )
   66: 
   67:         (princ
   68:             (strcat
   69:                 "\nУже существует: "
   70:                 LayerName
   71:             )
   72:         )
   73: 
   74:     )
   75: 
   76: )
   77: 
   78: 
   79: 
   80: ;=====================================================================
   81: ;
   82: ;                     ОСНОВНАЯ КОМАНДА
   83: ;
   84: ;=====================================================================
   85: 
   86: (defun C:LEP-SETUP (/)
   87: 
   88:     (princ "\n")
   89:     (princ "========================================")
   90:     (princ "\nПодготовка чертежа LEP")
   91:     (princ "\n========================================")
   92: 
   93: 
   94: 
   95:     ;;------------------------------------------------------------
   96:     ;; Подложка
   97:     ;;------------------------------------------------------------
   98: 
   99:     (LEP:CreateLayer
  100:         *LEP-Layer-Kadastr*
  101:         *LEP-Color-Kadastr*
  102:     )
  103: 
  104: 
  105: 
  106:     ;;------------------------------------------------------------
  107:     ;; Воздушные линии
  108:     ;;------------------------------------------------------------
  109: 
  110:     (LEP:CreateLayer
  111:         *LEP-Layer-Proj-VL*
  112:         *LEP-Color-Proj*
  113:     )
  114: 
  115:     (LEP:CreateLayer
  116:         *LEP-Layer-Exist-VL*
  117:         *LEP-Color-Exist*
  118:     )
  119: 
  120: 
  121: 
  122:     ;;------------------------------------------------------------
  123:     ;; Кабельные линии
  124:     ;;------------------------------------------------------------
  125: 
  126:     (LEP:CreateLayer
  127:         *LEP-Layer-Proj-KL*
  128:         *LEP-Color-Proj*
  129:     )
  130: 
  131:     (LEP:CreateLayer
  132:         *LEP-Layer-Exist-KL*
  133:         *LEP-Color-Exist*
  134:     )
  135: 
  136: 
  137: 
  138:     ;;------------------------------------------------------------
  139:     ;; Опоры
  140:     ;;------------------------------------------------------------
  141: 
  142:     (LEP:CreateLayer
  143:         *LEP-Layer-Proj-Pole*
  144:         *LEP-Color-Proj*
  145:     )
  146: 
  147:     (LEP:CreateLayer
  148:         *LEP-Layer-Exist-Pole*
  149:         *LEP-Color-Exist*
  150:     )
  151: 
  152: 
  153: 
  154:     ;;------------------------------------------------------------
  155:     ;; Подстанции
  156:     ;;------------------------------------------------------------
  157: 
  158:     (LEP:CreateLayer
  159:         *LEP-Layer-Proj-MTP*
  160:         *LEP-Color-Proj*
  161:     )
  162: 
  163:     (LEP:CreateLayer
  164:         *LEP-Layer-Proj-RLK*
  165:         *LEP-Color-Proj*
  166:     )
  167: 
  168:     (LEP:CreateLayer
  169:         *LEP-Layer-Proj-TP*
  170:         *LEP-Color-Proj*
  171:     )
  172: 
  173:     (LEP:CreateLayer
  174:         *LEP-Layer-Exist-TP*
  175:         *LEP-Color-Exist*
  176:     )
  177: 
  178: 
  179: 
  180:     ;;------------------------------------------------------------
  181:     ;; Текст
  182:     ;;------------------------------------------------------------
  183: 
  184:     (LEP:CreateLayer
  185:         *LEP-Layer-Text*
  186:         *LEP-Color-Text*
  187:     )
  188: 
  189: 
  190: 
  191:     ;;------------------------------------------------------------
  192:     ;; Размеры
  193:     ;;------------------------------------------------------------
  194: 
  195:     (LEP:CreateLayer
  196:         *LEP-Layer-Dim*
  197:         *LEP-Color-Dim*
  198:     )
  199: 
  200: 
  201: 
  202:     (princ)
  203: 
  204:     (princ "\n")
  205:     (princ "========================================")
  206:     (princ "\nПодготовка завершена.")
  207:     (princ "\n========================================")
  208: 
  209:     (princ)
  210: 
  211: )
~/Desktop/LEP LSP/LEP-SPAN.LSP:
    1: ;=====================================================================
    2: ; ПРОЕКТ:   LEP
    3: ; ФАЙЛ:     LEP-SPAN.LSP
    4: ; ВЕРСИЯ:   0.1
    5: ; НАЗНАЧЕНИЕ: Расчет пролетов, назначение слоев и расстановка подписей
    6: ;=====================================================================
    7: 
    8: ;; Функция округления числа вверх до ближайшего кратного (например, до 5.0)
    9: (defun LEP:RoundUp (Value Step / Remainder)
   10:     (setq Remainder (rem Value Step))
   11:     (if (= Remainder 0.0)
   12:         Value
   13:         (+ (- Value Remainder) Step)
   14:     )
   15: )
   16: 
   17: ;; Функция создания текста подписи пролета вдоль линии
   18: (defun LEP:CreateSpanText (P1 P2 TextString / MidPoint Ang)
   19:     ;; Находим центр пролета (средняя точка между опорами)
   20:     (setq MidPoint (list 
   21:         (/ (+ (car P1) (car P2)) 2.0)
   22:         (/ (+ (cadr P1) (cadr P2)) 2.0)
   23:         0.0
   24:     ))
   25:     
   26:     ;; Вычисляем угол наклона линии в радианax
   27:     (setq Ang (angle P1 P2))
   28:     
   29:     ;; Нормализуем угол, чтобы текст не читался "вверх ногами" (переворот при чтении справа налево)
   30:     (if (and (> Ang (/ PI 2.0)) (<= Ang (/ (* 3.0 PI) 2.0)))
   31:         (setq Ang (+ Ang PI))
   32:     )
   33: 
   34:     ;; Вставляем однострочный текст TEXT на слой подписей
   35:     (command "_.TEXT" 
   36:         "_Justify" "_BCenter"       ; Выравнивание по центру снизу (над линией)
   37:         MidPoint                     ; Точка вставки
   38:         *LEP-TextHeight* ; Высота текста из CONFIG
   39:         (angtos Ang 0 4)             ; Угол поворота в градусах текущей системы
   40:         TextString                   ; Сам текст подписи
   41:     )
   42: )
   43: 
   44: ;=====================================================================
   45: ; ГЛАВНАЯ КОМАНДА: LEP-SPAN
   46: ;=====================================================================
   47: (defun C:LEP-SPAN (/ RouteEnt Vertices TotalVertices i P1 P2 RealLen RoundLen Choice WireType TargetLayer TextLabel)
   48:     (LEP:PrintHeader "Обработка пролетов и подписи")
   49: 
   50:     (setq RouteEnt (car (entsel "\nВыберите полилинию маршрута для расчета пролетов: ")))
   51: 
   52:     (if (and RouteEnt (= (cdr (assoc 0 (entget RouteEnt))) "LWPOLYLINE"))
   53:         (progn
   54:             ;; 1. Запрос типа прокладки линии
   55:             (initget "1 2")
   56:             (setq Choice (getkword "\nТип прокладки: [1 - Воздух (ВЛ) / 2 - Земля (КЛ)]: "))
   57:             
   58:             (if (= Choice "1")
   59:                 (progn
   60:                     (setq WireType "СИП-2 95") ; В дальнейшем можно сделать выбор из CONFIG
   61:                     (setq TargetLayer *LEP-Layer-Proj-VL*)
   62:                 )
   63:                 (progn
   64:                     (setq WireType "Кабель 120")
   65:                     (setq TargetLayer *LEP-Layer-Proj-KL*)
   66:                 )
   67:             )
   68: 
   69:             ;; 2. Меняем слой самого маршрута на правильный тип прокладки
   70:             (command "_.CHPROP" RouteEnt "" "_Layer" TargetLayer "")
   71: 
   72:             ;; 3. Бежим по сегментам полилинии и ставим подписи
   73:             (setq Vertices (LEP:GetVertices RouteEnt))
   74:             (setq TotalVertices (length Vertices))
   75:             (setq i 0)
   76: 
   77:             (LEP:SetCurrentLayer *LEP-Layer-Text*)
   78: 
   79:             (repeat (- TotalVertices 1)
   80:                 (setq P1 (nth i Vertices))
   81:                 (setq P2 (nth (+ i 1) Vertices))
   82:                 
   83:                 ;; Считаем честное расстояние (1 ед. = 1 метр благодаря LEP-SCALE)
   84:                 (setq RealLen (distance P1 P2))
   85:                 
   86:                 ;; Округляем вверх по правилу из CONFIG (например, до ближайших 5 метров)
   87:                 (setq RoundLen (fix (LEP:RoundUp RealLen *LEP-LengthRound*)))
   88: 
   89:                 ;; Собираем сквозную инженерную подпись под ЧБ-печать
   90:                 (setq TextLabel (strcat *LEP-TextPrefix-Proj* WireType " - " (itoa RoundLen) " м"))
   91:                 
   92:                 ;; Генерируем текст на чертеже
   93:                 (LEP:CreateSpanText P1 P2 TextLabel)
   94: 
   95:                 (setq i (1+ i))
   96:             )
   97:             (princ (strcat "\nУспешно обработано пролетов: " (itoa i)))
   98:         )
   99:         (princ "\nОшибка: Нужно выбрать объект типа Полилиния.")
  100:     )
  101: 
  102:     (LEP:PrintFooter)
  103:     (princ)
  104: )
  105: 
  106: (princ "\nLEP-SPAN v0.1 загружен.")
  107: (princ)
~/Desktop/LEP LSP/LEP-START.LSP:
    1: ;=====================================================================
    2: ;
    3: ;   ПРОЕКТ:
    4: ;   LEP
    5: ;
    6: ;   ФАЙЛ:
    7: ;   LEP-START.LSP
    8: ;
    9: ;   НАЗНАЧЕНИЕ:
   10: ;
   11: ;   Главный загрузчик проекта LEP.
   12: ;
   13: ;   Пользователь загружает только этот файл.
   14: ;
   15: ;   Все остальные модули подключаются автоматически.
   16: ;
   17: ;=====================================================================
   18: 
   19: 
   20: 
   21: ;=====================================================================
   22: ;
   23: ; НАСТРОЙКА ПАПКИ ПРОЕКТА
   24: ;
   25: ; Вариант 1:
   26: ; Все файлы лежат в одной папке.
   27: ;
   28: ; В дальнейшем можно заменить на автоматический
   29: ; поиск папки текущего LSP.
   30: ;
   31: ;=====================================================================
   32: 
   33: 
   34: (setq *LEP-Path*
   35: 
   36:     (getvar "DWGPREFIX")
   37: 
   38: )
   39: 
   40: 
   41: 
   42: ;=====================================================================
   43: ;
   44: ; ФУНКЦИЯ ЗАГРУЗКИ ФАЙЛА
   45: ;
   46: ; Проверяет наличие файла и загружает его.
   47: ;
   48: ;=====================================================================
   49: 
   50: 
   51: (defun LEP:LoadFile (FileName / FullPath)
   52: 
   53:     (setq FullPath
   54: 
   55:         (strcat
   56: 
   57:             *LEP-Path*
   58: 
   59:             FileName
   60: 
   61:         )
   62: 
   63:     )
   64: 
   65: 
   66:     (if
   67: 
   68:         (findfile FullPath)
   69: 
   70:         (progn
   71: 
   72:             (load FullPath)
   73: 
   74:             (princ
   75: 
   76:                 (strcat
   77: 
   78:                     "\nЗагружен: "
   79: 
   80:                     FileName
   81: 
   82:                 )
   83: 
   84:             )
   85: 
   86:         )
   87: 
   88: 
   89:         (princ
   90: 
   91:             (strcat
   92: 
   93:                 "\nНЕ НАЙДЕН: "
   94: 
   95:                 FullPath
   96: 
   97:             )
   98: 
   99:         )
  100: 
  101:     )
  102: 
  103: )
  104: 
  105: 
  106: 
  107: ;=====================================================================
  108: ;
  109: ; ЗАПУСК ЗАГРУЗКИ
  110: ;
  111: ; Порядок важен!
  112: ;
  113: ; 1. CONFIG
  114: ;    настройки
  115: ;
  116: ; 2. UTILS
  117: ;    общие функции
  118: ;
  119: ; 3. SETUP
  120: ;    подготовка чертежа
  121: ;
  122: ; 4. POLYLINE
  123: ;    работа с маршрутами
  124: ;
  125: ; 5. POLE
  126: ;    установка опор
  127: ;
  128: ; 6. SPAN
  129: ;    работа с пролетами
  130: ;
  131: ; 7. SCALE
  132: ;    установка масштаба подложки
  133: ;
  134: ; 8. REPORT
  135: ;    считает ведомость опор кабелей и проводов
  136: ;
  137: ;=====================================================================
  138: 
  139: 
  140: (princ "\n")
  141: (princ "======================================")
  142: (princ "\n Загрузка системы LEP")
  143: (princ "\n======================================")
  144: 
  145: 
  146: (LEP:LoadFile "LEP-CONFIG.LSP")
  147: 
  148: (LEP:LoadFile "LEP-UTILS.LSP")
  149: 
  150: (LEP:LoadFile "LEP-SETUP.LSP")
  151: 
  152: (LEP:LoadFile "LEP-POLYLINE.LSP")
  153: 
  154: (LEP:LoadFile "LEP-POLE.LSP")
  155: 
  156: (LEP:LoadFile "LEP-SPAN.LSP")
  157: 
  158: (LEP:LoadFile "LEP-SCALE.LSP")
  159: 
  160: (LEP:LoadFile "LEP-REPORT.LSP")
  161: 
  162: 
  163: 
  164: (princ "\n")
  165: (princ "======================================")
  166: (princ "\n LEP загружен успешно")
  167: (princ "\n Команды:")
  168: (princ "\n LEP-SETUP")
  169: (princ "\n LEP-ROUTE")
  170: (princ "\n LEP-POLE")
  171: (princ "\n LEP-SPAN")
  172: (princ "\n LEP-SCALE")
  173: (princ "\n LEP-REPORT")
  174: (princ "\n======================================")
  175: 
  176: 
  177: (princ)
~/Desktop/LEP LSP/LEP-UTILS.LSP:
    1: ;=====================================================================
    2: ;
    3: ;   ПРОЕКТ:      LEP
    4: ;
    5: ;   ФАЙЛ:        LEP-UTILS.LSP
    6: ;
    7: ;   ВЕРСИЯ:      0.1
    8: ;
    9: ;   НАЗНАЧЕНИЕ:
   10: ;
   11: ;   Общие служебные функции проекта.
   12: ;
   13: ;   Данные функции не являются самостоятельными командами.
   14: ;
   15: ;   Они используются всеми остальными модулями проекта.
   16: ;
   17: ;=====================================================================
   18: 
   19: 
   20: 
   21: ;=====================================================================
   22: ;                     LEP:LayerExists
   23: ;
   24: ; Проверяет существование слоя.
   25: ;
   26: ; Вход:
   27: ;   LayerName
   28: ;
   29: ; Выход:
   30: ;   T
   31: ;   nil
   32: ;
   33: ;=====================================================================
   34: 
   35: (defun LEP:LayerExists (LayerName)
   36: 
   37:     (if (tblsearch "LAYER" LayerName)
   38:         T
   39:         nil
   40:     )
   41: 
   42: )
   43: 
   44: 
   45: 
   46: ;=====================================================================
   47: ;                     LEP:BlockExists
   48: ;
   49: ; Проверяет наличие блока.
   50: ;
   51: ;=====================================================================
   52: 
   53: (defun LEP:BlockExists (BlockName)
   54: 
   55:     (if (tblsearch "BLOCK" BlockName)
   56:         T
   57:         nil
   58:     )
   59: 
   60: )
   61: 
   62: 
   63: 
   64: ;=====================================================================
   65: ;                     LEP:SetCurrentLayer
   66: ;
   67: ; Делает слой текущим.
   68: ;
   69: ;=====================================================================
   70: 
   71: (defun LEP:SetCurrentLayer (LayerName)
   72: 
   73:     (if (LEP:LayerExists LayerName)
   74: 
   75:         (setvar "CLAYER" LayerName)
   76: 
   77:         (princ
   78:             (strcat
   79:                 "\nОшибка. Слой "
   80:                 LayerName
   81:                 " не существует."
   82:             )
   83:         )
   84: 
   85:     )
   86: 
   87: )
   88: 
   89: 
   90: 
   91: ;=====================================================================
   92: ;                     LEP:RoundLength
   93: ;
   94: ; Округление длины до ближайшего значения.
   95: ;
   96: ; Например
   97: ;
   98: ; 22 -> 20
   99: ; 23 -> 25
  100: ;
  101: ; Используется переменная
  102: ;
  103: ; *LEP-LengthRound*
  104: ;
  105: ;=====================================================================
  106: 
  107: (defun LEP:RoundLength (Value /)
  108: 
  109:     (*
  110: 
  111:         *LEP-LengthRound*
  112: 
  113:         (fix
  114: 
  115:             (+
  116: 
  117:                 (/ Value *LEP-LengthRound*)
  118: 
  119:                 0.5
  120: 
  121:             )
  122: 
  123:         )
  124: 
  125:     )
  126: 
  127: )
  128: 
  129: 
  130: 
  131: ;=====================================================================
  132: ;                     LEP:PrintHeader
  133: ;
  134: ; Красивый заголовок команды.
  135: ;
  136: ;=====================================================================
  137: 
  138: (defun LEP:PrintHeader (Title)
  139: 
  140:     (princ "\n")
  141: 
  142:     (princ "==========================================")
  143: 
  144:     (princ
  145:         (strcat
  146:             "\n"
  147:             Title
  148:         )
  149:     )
  150: 
  151:     (princ "\n==========================================")
  152: 
  153: )
  154: 
  155: 
  156: 
  157: ;=====================================================================
  158: ;                     LEP:PrintFooter
  159: ;
  160: ;=====================================================================
  161: 
  162: (defun LEP:PrintFooter ()
  163: 
  164:     (princ "\n==========================================")
  165: 
  166:     (princ "\nГотово.")
  167: 
  168:     (princ "\n==========================================")
  169: 
  170: )
  171: 
  172: 
  173: 
  174: ;=====================================================================
  175: ;                     LEP:GetDistance
  176: ;
  177: ; Возвращает расстояние между двумя точками.
  178: ;
  179: ; Сделано отдельной функцией потому что потом сюда
  180: ; можно добавить коэффициенты, проверки и т.п.
  181: ;
  182: ;=====================================================================
  183: 
  184: (defun LEP:GetDistance (P1 P2)
  185: 
  186:     (distance P1 P2)
  187: 
  188: )
  189: 
  190: 
  191: 
  192: ;=====================================================================
  193: ;                     LEP:Message
  194: ;
  195: ; Унифицированный вывод сообщений.
  196: ;
  197: ;=====================================================================
  198: 
  199: (defun LEP:Message (Text)
  200: 
  201:     (princ
  202: 
  203:         (strcat
  204: 
  205:             "\n[LEP] "
  206: 
  207:             Text
  208: 
  209:         )
  210: 
  211:     )
  212: 
  213: )
  214: 
  215: 
  216: 
  217: ;=====================================================================
  218: ;                     LEP:Error
  219: ;
  220: ; Общий обработчик ошибок.
  221: ;
  222: ; Пока простой.
  223: ;
  224: ; Позже сюда добавим восстановление системных
  225: ; переменных и откат временных изменений.
  226: ;
  227: ;=====================================================================
  228: 
  229: (defun LEP:Error (Msg)
  230: 
  231:     (princ)
  232: 
  233:     (princ
  234:         (strcat
  235: 
  236:             "\nОшибка: "
  237: 
  238:             Msg
  239: 
  240:         )
  241:     )
  242: 
  243:     (princ)
  244: 
  245: )
  246: 
  247: 
  248: 
  249: (princ "\nLEP-UTILS загружен.")
  250: 
  251: (princ)
22 matches across 11 files
