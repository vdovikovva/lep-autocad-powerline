;=====================================================================
;
;   ПРОЕКТ:      LEP
;   ФАЙЛ:        LEP-TEST-SCENE.LSP
;   НАЗНАЧЕНИЕ:  ИСПЫТАТЕЛЬНЫЙ СТЕНД, НЕ ЧАСТЬ ПРОГРАММЫ
;
;   ⚠️ ЭТОТ ФАЙЛ НЕ ГРУЗИТСЯ АВТОМАТИЧЕСКИ. В LEP-START.LSP список
;   модулей задан явным перечислением, и этого файла там нет - грузить
;   вручную через APPLOAD, только когда нужен тест.
;
;   ⚠️ ЗАПУСКАТЬ ТОЛЬКО НА ПУСТОМ ЧЕРТЕЖЕ. Скрипт ничего не удаляет и
;   не портит, но строит целую сцену - на боевом чертеже она будет
;   мешаться. Убирать её проще всего закрытием чертежа без сохранения.
;
;=====================================================================
;
;   ЗАЧЕМ ЭТО НУЖНО
;
;   Проверяем параллельный сдвиг проводов на общем участке двух
;   маршрутов. Воспроизвести сценарий руками - это два десятка кликов,
;   и каждый раз чуть по-другому: то вершина ляжет ровно на опору, то
;   мимо. А разница между "ровно" и "мимо" - как раз то, что мы и
;   проверяем, случайной она быть не должна.
;
;   Сцена повторяет реальный чертёж пользователя:
;     - маршрут 1 идёт по существующим опорам до существующей ТП;
;     - маршрут 2 начинается на своей улице, вливается в маршрут 1 и
;       дальше идёт с ним по ОБЩИМ опорам до той же ТП.
;
;   ⚠️ ПЕРЕДЕЛАНО 2026-08-06 ПО ЗАМЕЧАНИЯМ ПОЛЬЗОВАТЕЛЯ. Первая версия
;   сцены была неправильной в двух местах сразу, и на ней нельзя было
;   ничего проверить:
;
;   БЫЛО: маршрут 2 ломался на пустом месте, между опорами.
;   СТАЛО: излом ТОЛЬКО НА ОПОРЕ. Дословно: "это же ВЛ, она не может
;   пересечься и изменить направление без опоры". Место слияния - это
;   СУЩЕСТВУЮЩАЯ ОПОРА МАРШРУТА 1, на ней маршрут 2 и поворачивает.
;
;   БЫЛО: маршрут 2 шёл в 0,2-0,4 м от маршрута 1 - я имитировал промах
;   руки.
;   СТАЛО: маршруты на общем участке СОВПАДАЮТ ТОЧНО. Дословно:
;   "маршруты будут в месте пересечения лежать друг на друге, а вот
;   трассы (пролёты) уже должны отступать". И это правильнее: маршрут -
;   служебная геометрия на непечатаемом слое, арматура для привязки
;   опор. Два фидера на одних опорах физически идут по одной линии.
;   А расхождение на 0,3 м - условность оформления, чтобы на бумаге
;   читались два провода; ей место в пролёте, а не в трассе.
;
;   ⚠️ ПОСЛЕДСТВИЕ, КОТОРОЕ ВАЖНО ПОНИМАТЬ ПРИ ЧТЕНИИ РЕЗУЛЬТАТОВ:
;   раз ВЛ не гнётся без опоры, то на общем участке маршруту 2 гнуться
;   негде - он идёт туда ОДНИМ ПРЯМЫМ ОТРЕЗКОМ от опоры слияния до ТП.
;   Промежуточных вершин у него там нет вообще. Значит его единственный
;   длинный отрезок ложится ПОВЕРХ нескольких коротких размеров
;   маршрута 1 - это не "задвоилось", а "перекрыло", и проверять надо
;   именно такой случай.
;
;   ⚠️ ЧТО ОСТАЛОСЬ НАМЕРЕННЫМ: координаты сцены БОЛЬШИЕ (около
;   2 247 000 / 454 600, зона МСК-47, как на реальных чертежах), а не
;   около нуля. Если где-то вылезет потеря точности на больших числах,
;   пусть вылезет в тесте, а не на боевом чертеже.
;
;=====================================================================
;
;   КОМАНДЫ
;
;   LEP-TEST-SCENE   строит сцену (маршруты, опоры, ТП)
;
;   Пролёты кликаются РУКАМИ через LEP-SPAN - это и есть то, что
;   проверяем. Сначала маршрут 1 (первая опора -> ТП), потом маршрут 2
;   (его первая опора -> та же ТП).
;
;   ⚠️ Команды LEP-TEST-OFFSET-DEMO и LEP-TEST-CLEAN УБРАНЫ 2026-08-06.
;   Они рисовали два варианта сдвига на выбор - "сдвинуть весь пролёт"
;   против "сдвинуть только перекрытую часть". Выбор отпал: сдвиг
;   считается посегментно, и второй вариант получается единственно
;   возможным. Держать картинку-макет рядом с работающим кодом значит
;   однажды поверить макету вместо кода. Плюс демо рисовало обе линии
;   в ОДНУ сторону и этим само вводило в заблуждение - пользователь
;   резонно спросил, почему не меняется сторонность.
;
;=====================================================================


;; Базовая точка сцены. Все координаты ниже задаются СМЕЩЕНИЕМ от неё,
;; в метрах - так их видно и можно править, не считая семизначные числа.
(setq *LEP-Test-Base* (list 2247000.0 454600.0))


;=====================================================================
; LEP:TP - точка сцены по смещению от базовой, в метрах
;=====================================================================

(defun LEP:TP (Dx Dy)
    (list
        (+ (car  *LEP-Test-Base*) Dx)
        (+ (cadr *LEP-Test-Base*) Dy)
    )
)


;=====================================================================
; LEP:TestDrawRoute
;
; Рисует полилинию маршрута и вешает на неё XDATA - ровно тем же
; способом, что и C:LEP-ROUTE: команда _.PLINE на служебном слое, потом
; LEP:AddRoute. Через entmake делать НЕ стал специально: чем ближе
; тестовая сцена к настоящему пути создания, тем меньше шансов, что
; тест пройдёт на объектах, которых в реальной работе не бывает.
;
; Возвращает список (ename ID).
;=====================================================================

(defun LEP:TestDrawRoute (Pts VClass / OldLayer Ent ID P)

    (setq OldLayer (getvar "CLAYER"))
    (LEP:SetCurrentLayer *LEP-Layer-Route*)

    (command "_.PLINE")
    (foreach P Pts (command P))
    (command "")

    (setq Ent (entlast))
    (setq ID (LEP:AddRoute Ent VClass))
    (LEP:CreateRouteLabel (car Pts) ID)

    (setvar "CLAYER" OldLayer)

    (list Ent ID)
)


;=====================================================================
; C:LEP-TEST-SCENE
;
; ГЕОМЕТРИЯ СЦЕНЫ (смещения от базовой точки, метры):
;
;   маршрут 1:  (0,0) ──────────●────────────────── (300,0)=ТП
;               опоры на 0, 45, 95, 140, 185, 230, 265
;                                    ↑
;                              опора слияния
;
;   маршрут 2:  (40,-140) ─ (75,-105) ─ (110,-70) ─ (145,-35) ─ (185,0)
;               свои опоры на каждой вершине         ↑ и дальше ОДНИМ
;                                                      ПРЯМЫМ ОТРЕЗКОМ
;                                                      до (300,0)=ТП
;
; ⚠️ ВСЕ ИЗЛОМЫ МАРШРУТА 2 - НА ОПОРАХ. Последний излом, на отметке
; 185, приходится РОВНО на существующую опору маршрута 1: там фидеры и
; сходятся. Своей опоры маршрут 2 туда не ставит - опора уже есть,
; она одна физическая.
;
; ⚠️ НА ОБЩЕМ УЧАСТКЕ (185 -> 300) МАРШРУТЫ СОВПАДАЮТ ТОЧНО, зазора
; нет. Расходиться должны пролёты, а не трассы.
;
; ⚠️ У МАРШРУТА 2 НА ОБЩЕМ УЧАСТКЕ НЕТ НИ ОДНОЙ ПРОМЕЖУТОЧНОЙ ВЕРШИНЫ -
; гнуться ему там негде, ВЛ идёт прямо. Поэтому его ОДИН отрезок
; 185->300 накрывает СРАЗУ ТРИ размера маршрута 1 (185-230, 230-265,
; 265-300). Это главный случай, ради которого сцена и собрана: и
; проверка дублей размеров, и подсчёт перекрытия для сдвига должны
; правильно отработать "один длинный поверх нескольких коротких".
;
; ⚠️ Опоры маршрута 2 стоят через ~50 м (а не через 145, как в первой
; версии сцены): пролёт ВЛ в полтораста метров - это не то, что бывает
; на реальном чертеже, и размеры на нём выглядели бы неправдоподобно.
;=====================================================================

(defun C:LEP-TEST-SCENE (/ OldOs OldLayer R1 R2 Route1 ID1 Route2 ID2 Dx P
                           VClass ClassLabel TpPt InsertResult Pt1 KtpEnt)

    (LEP:PrintHeader "ТЕСТОВАЯ СЦЕНА: два маршрута с общим участком")

    (setq VClass "10")
    (setq ClassLabel (cdr (assoc VClass *LEP-VoltageClassLabel*)))

    ;; Привязки выключаем на время построения: сцена задаётся точными
    ;; координатами, и притягивание к уже нарисованному нам тут только
    ;; помешает. В конце возвращаем как было.
    (setq OldOs (getvar "OSMODE"))
    (setq OldLayer (getvar "CLAYER"))
    (setvar "OSMODE" 0)

    ;-----------------------------------------------------------------
    ; МАРШРУТ 1 - прямой, с востока на запад
    ;-----------------------------------------------------------------
    (princ "\n[ТЕСТ] Маршрут 1...")
    (setq R1 (LEP:TestDrawRoute (list (LEP:TP 0.0 0.0) (LEP:TP 300.0 0.0)) VClass))
    (setq Route1 (car R1))
    (setq ID1 (cadr R1))

    ;-----------------------------------------------------------------
    ; СУЩЕСТВУЮЩИЕ ОПОРЫ МАРШРУТА 1
    ;
    ; Статус EXIST - сценарий коллеги именно такой: новый провод идёт по
    ; уже стоящим опорам.
    ;-----------------------------------------------------------------
    (princ "\n[ТЕСТ] Опоры маршрута 1...")
    (foreach Dx '(0.0 45.0 95.0 140.0 185.0 230.0 265.0)
        (LEP:PlacePoleOnRoute Route1 ID1 ClassLabel (LEP:TP Dx 0.0) "П23" "EXIST" VClass)
    )

    ;-----------------------------------------------------------------
    ; СУЩЕСТВУЮЩАЯ ТП В КОНЦЕ МАРШРУТА 1
    ;
    ; Повторяет ветку КТП из C:LEP-END: вершина на маршруте, символ,
    ; подпись, XDATA. Значения (номер, мощность, марка) взяты
    ; произвольные - на проверку сдвига они не влияют никак, а высокая
    ; сторона берётся первым пунктом из *LEP-KTP-HighSide*, чтобы не
    ; угадывать её код руками.
    ;
    ; ⚠️ ОДНО ОТЛИЧИЕ ОТ БОЕВОГО C:LEP-END: не накладывается
    ; GEOMCONSTRAINT между символом ТП и вершиной маршрута. Для теста
    ; сдвига это безразлично (связь нужна, чтобы символ ехал за
    ; вершиной при редактировании трассы, а мы её не двигаем), но если
    ; на этой же сцене начнёшь проверять что-то про перемещение
    ; объектов - помни, что связи тут нет.
    ;-----------------------------------------------------------------
    (princ "\n[ТЕСТ] ТП...")
    (setq TpPt (LEP:TP 300.0 0.0))
    (setq InsertResult (LEP:InsertVertexOnRoute Route1 TpPt))
    (setq Pt1 (car InsertResult))
    (setq KtpEnt (LEP:InsertKtpSymbol Pt1 "EXIST"))
    (if KtpEnt
        (progn
            (LEP:CreateKtpLabel Pt1 "EXIST" "5766" 160.0 (cdr (car *LEP-KTP-HighSide*)) "ТМГ-160")
            (LEP:AddKtpData KtpEnt ID1 "EXIST" "5766" 160.0 "ТМГ-160" (cdr (car *LEP-KTP-HighSide*)))
        )
    )

    ;-----------------------------------------------------------------
    ; МАРШРУТ 2 - своя улица, слияние, общий участок до той же ТП
    ;
    ; ⚠️ Последняя вершина - РОВНО точка ТП. Без этого геометрический
    ; поиск маршрута (LEP:FindRoutesThroughPoints) не признал бы
    ; маршрут 2 проходящим через оба конца будущего пролёта, и мы бы
    ; тестировали не то.
    ;-----------------------------------------------------------------
    (princ "\n[ТЕСТ] Маршрут 2...")
    (setq R2
        (LEP:TestDrawRoute
            (list
                (LEP:TP  40.0 -140.0)
                (LEP:TP  75.0 -105.0)
                (LEP:TP 110.0  -70.0)
                (LEP:TP 145.0  -35.0)
                (LEP:TP 185.0    0.0)   ; излом РОВНО на опоре маршрута 1
                (LEP:TP 300.0    0.0)   ; и сразу ТП, без промежуточных вершин
            )
            VClass
        )
    )
    (setq Route2 (car R2))
    (setq ID2 (cadr R2))

    ;-----------------------------------------------------------------
    ; ОПОРЫ МАРШРУТА 2 - ТОЛЬКО НА ЕГО СОБСТВЕННОЙ УЛИЦЕ
    ;
    ; ⚠️ На общем участке своих опор у маршрута 2 НЕТ И БЫТЬ НЕ ДОЛЖНО -
    ; там висят провода обоих фидеров на опорах маршрута 1. Поставь я
    ; их сюда "для красоты" - сцена перестала бы воспроизводить задачу.
    ;
    ; ⚠️ И НА САМОЙ ОПОРЕ СЛИЯНИЯ (185) ТОЖЕ НЕ СТАВИМ. Опора там уже
    ; есть - она принадлежит маршруту 1, и физически она ОДНА. Вторая
    ; опора в той же точке была бы не "подстраховкой", а лишней штукой
    ; в ведомости и вторым символом поверх первого.
    ;
    ; Шаг ~50 м: в первой версии сцены между опорами маршрута 2
    ; получалось до 145 м - для ВЛ это неправдоподобно, и размеры на
    ; таком пролёте выглядели бы неправильно.
    ;-----------------------------------------------------------------
    (princ "\n[ТЕСТ] Опоры маршрута 2...")
    (foreach P (list (LEP:TP 40.0 -140.0) (LEP:TP 75.0 -105.0)
                     (LEP:TP 110.0 -70.0) (LEP:TP 145.0 -35.0))
        (LEP:PlacePoleOnRoute Route2 ID2 ClassLabel P "П23" "EXIST" VClass)
    )

    (setvar "OSMODE" OldOs)
    (setvar "CLAYER" OldLayer)
    (command "_.ZOOM" "_Extents")

    (princ (strcat "\n[ТЕСТ] Готово. Маршрут 1 = " ID1 ", маршрут 2 = " ID2 "."))
    (princ "\n[ТЕСТ] Дальше руками: LEP-SPAN, пролёт маршрута 1 (первая опора -> ТП),")
    (princ "\n[ТЕСТ] потом пролёт маршрута 2 (его первая опора -> та же ТП).")
    (princ "\n[ТЕСТ] Трассы не видно - это норма, слой непечатаемый. Показать: LEP-ROUTEVIS.")
    (princ)
)


(princ "\nЗагружен ИСПЫТАТЕЛЬНЫЙ СТЕНД. Команда: LEP-TEST-SCENE")
(princ)
