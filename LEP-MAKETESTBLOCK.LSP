;=====================================================================
;
;   ПРОЕКТ:      LEP
;   ФАЙЛ:        LEP-MAKETESTBLOCK.LSP
;   ВЕРСИЯ:      0.1
;
;   НАЗНАЧЕНИЕ:
;   Создаёт простой тестовый блок "test-block" (кружок + атрибут с
;   тегом TIP) прямо кодом, через entmake - без захода в редактор
;   блоков. Нужен, чтобы тестировать LEP-POLE, пока не готов
;   настоящий блок опоры (oVkILj) с атрибутом.
;
;   ЭТО ВРЕМЕННЫЙ ФАЙЛ. Когда решите вопрос с реальным блоком опоры -
;   этот файл можно не грузить вообще (не добавляйте его в
;   LEP-START.LSP на постоянной основе).
;
;   КАК ИСПОЛЬЗОВАТЬ:
;   1. Загрузите этот файл через APPLOAD (отдельно от LEP-START).
;   2. Выполните команду LEP-MAKETESTBLOCK - один раз на чертёж,
;      она создаст блок "test-block" в текущем DWG.
;   3. В LEP-CONFIG.LSP временно поменяйте:
;        (setq *LEP-Block-Pole* "test-block")
;      (было "oVkILj" - когда вернётесь к реальному блоку, верните
;      обратно эту же строку).
;   4. Перезагрузите LEP-START.LSP и пробуйте LEP-POLE заново.
;
;=====================================================================

(defun C:LEP-MAKETESTBLOCK (/)

    (if (tblsearch "BLOCK" "test-block")
        (princ "\nБлок \"test-block\" уже существует в этом чертеже, ничего не создаю.")
        (progn
            ;; Начало определения блока. Точка вставки блока (10) -
            ;; это (0 0 0) в локальной системе координат самого блока -
            ;; именно от неё будет считаться точка вставки при -INSERT,
            ;; и именно к ней потом привязывается GEOMCONSTRAINT.
            (entmake
                (list
                    (cons 0 "BLOCK")
                    (cons 2 "test-block")   ; имя блока
                    (cons 70 0)             ; обычный блок (не анонимный, не xref)
                    (cons 10 (list 0.0 0.0 0.0))
                    (cons 8 "0")
                )
            )

            ;; Геометрия - простой кружок радиусом 0.5 (в единицах
            ;; чертежа - после калибровки это 0.5 м, для теста нормально).
            (entmake
                (list
                    (cons 0 "CIRCLE")
                    (cons 8 "0")
                    (cons 10 (list 0.0 0.0 0.0))
                    (cons 40 0.5)
                )
            )

            ;; Атрибут с тегом TIP - именно этот тег ожидает
            ;; *LEP-Block-Pole-AttTag* в LEP-CONFIG.LSP. Значение по
            ;; умолчанию не важно - LEP:SetBlockAttribute его перепишет
            ;; сразу после вставки.
            (entmake
                (list
                    (cons 0 "ATTDEF")
                    (cons 8 "0")
                    (cons 10 (list 0.0 -1.0 0.0))  ; точка текста - чуть ниже кружка
                    (cons 40 0.3)                   ; высота текста
                    (cons 1 "ТИП")                  ; значение по умолчанию
                    (cons 2 "TIP")                  ; ТЕГ атрибута
                    (cons 3 "Тип опоры")             ; подсказка
                    (cons 70 0)                     ; 0 = видимый атрибут
                )
            )

            (entmake (list (cons 0 "ENDBLK") (cons 8 "0")))

            (princ "\nБлок \"test-block\" создан (кружок + атрибут TIP).")
        )
    )

    (princ)
)

(princ "\nLEP-MAKETESTBLOCK загружен. Выполните LEP-MAKETESTBLOCK, затем поправьте *LEP-Block-Pole* в CONFIG.")
(princ)
