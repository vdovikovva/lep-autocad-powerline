;=====================================================================
;
;   ПРОЕКТ:      LEP
;   ФАЙЛ:        LEP-TRANSSYM.LSP
;   ВЕРСИЯ:      0.1  (первая версия - Claude, 2026-07-24)
;
;   НАЗНАЧЕНИЕ:
;   Символ ТОЧКИ СМЕНЫ СПОСОБА ПРОКЛАДКИ - маленький кружок
;   (*LEP-Trans-Diameter*, LEP-CONFIG.LSP) на НЕПЕЧАТАЕМОМ слое
;   *LEP-Layer-Transition*.
;
;   ЗАЧЕМ (реальный случай пользователя 2026-07-24):
;   трасса от КТП идёт под углом 90°, первый участок надо пройти ГНБ
;   (проколом), второй - обычной траншеей. Способ прокладки
;   спрашивается ОДИН РАЗ НА ПРОЛЁТ, а пролёт задаётся ДВУМЯ
;   ОБЪЕКТАМИ - значит, чтобы поделить кабельный участок надвое,
;   в точке перехода должен стоять хоть какой-то объект, за который
;   можно "зацепить" конец пролёта. Опоры там нет и быть не должно
;   (её посчитала бы ведомость), КТП/киоск - тем более. Отсюда этот
;   маркер: пустышка без всякого смысла для сметы, нужная ТОЛЬКО как
;   точка стыковки двух пролётов.
;
;   ⚠️ ПОЧЕМУ ЭТО БЛОК, А НЕ ПРОСТО КРУЖОК (CIRCLE).
;   Кружок сам по себе тоже подошёл бы: у CIRCLE группа DXF 10 - это
;   центр, то есть LEP:PickPole (LEP-SPAN.LSP) достал бы из него точку
;   ровно так же, как достаёт точку вставки блока. Но LEP:PickPole
;   проверяет, что выбранный объект - именно INSERT, и это НЕ придирка,
;   а полезный инвариант: "любой конец пролёта - блок с XDATA". Пока он
;   держится, туда физически не может попасть случайная линия подосновы
;   или обрывок чужой геометрии. Ради одного кружка ломать инвариант
;   невыгодно - дешевле завернуть кружок в блок, как сделано у опоры,
;   КТП и киоска.
;
;   ⚠️ Блок, как и остальные символы проекта, создаётся ТОЛЬКО ЕСЛИ
;   ЕЩЁ НЕ СУЩЕСТВУЕТ - НЕ передефайнится при повторной загрузке (см.
;   подробное обоснование в LEP-POLESYM.LSP).
;
;   ⚠️ Толщина линии по статусу тут СОЗНАТЕЛЬНО не выставляется (в
;   отличие от опоры/КТП/киоска): слой всё равно непечатаемый, в PDF
;   этот кружок не попадает, и разница "Проект. жирнее Сущ." на нём
;   не имеет смысла.
;
;=====================================================================

(setq *LEP-Block-Trans* "LEP-TRANS-SYM")


;=====================================================================
; LEP:CreateTransSymbolBlock
;
; Создаёт блок-символ точки смены способа прокладки
; (*LEP-Block-Trans*) - один кружок с центром в точке вставки блока
; (0,0,0), тот же принцип "точка вставки = геометрический центр", что
; у символов опоры/КТП/киоска.
;
; Цвет кружка задан ПРЯМО В ГЕОМЕТРИИ блока (группа DXF 62), а не
; ByLayer - тот же приём, что у серого креста опоры: цвет маркера
; фиксированный и от статуса не зависит.
;=====================================================================

(defun LEP:CreateTransSymbolBlock ()

    (if (not (tblsearch "BLOCK" *LEP-Block-Trans*))
        (progn
            (entmake
                (list
                    (cons 0 "BLOCK")
                    (cons 2 *LEP-Block-Trans*)
                    (cons 70 0)
                    (cons 10 (list 0.0 0.0 0.0))
                    (cons 8 "0")
                )
            )

            (entmake
                (list
                    '(0 . "CIRCLE")
                    (cons 8 "0")
                    (cons 62 *LEP-Color-Transition*)
                    (cons 10 (list 0.0 0.0 0.0))
                    (cons 40 (/ *LEP-Trans-Diameter* 2.0))
                )
            )

            (entmake (list (cons 0 "ENDBLK") (cons 8 "0")))

            (princ (strcat "\n[LEP-TRANSSYM] Создан блок-символ точки смены прокладки: " *LEP-Block-Trans*))
        )
    )
)


;=====================================================================
; LEP:InsertTransSymbol
;
; Вставляет маркер в точку Point. Слой ВСЕГДА ОДИН - непечатаемый
; *LEP-Layer-Transition*, независимо от статуса: маркер не бывает
; "существующим" или "проектируемым", он вообще не про материал, а
; про то, где кончается один вид работ и начинается другой.
;
; Возвращает ename вставленного блока - вызывающая сторона
; (LEP-END.LSP) использует его для GEOMCONSTRAINT и XDATA
; (LEP:AddTransData).
;=====================================================================

(defun LEP:InsertTransSymbol (Point)

    (entmake
        (list
            '(0 . "INSERT")
            (cons 8 *LEP-Layer-Transition*)
            (cons 2 *LEP-Block-Trans*)
            (cons 10 (list (car Point) (cadr Point) 0.0))
            (cons 41 1.0)
            (cons 42 1.0)
            (cons 43 1.0)
            (cons 50 0.0)
        )
    )

    (entlast)
)


(princ "\nLEP-TRANSSYM v0.1 загружен (маркер смены способа прокладки - непечатаемый кружок).")
(princ)
