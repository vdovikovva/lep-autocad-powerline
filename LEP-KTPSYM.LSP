;=====================================================================
;
;   ПРОЕКТ:      LEP
;   ФАЙЛ:        LEP-KTPSYM.LSP
;   ВЕРСИЯ:      0.3  (толщина линии по статусу - LEP:SetEntityLWeight,
;                тот же приём, что и у символа опоры, Claude, 2026-07-22)
;   0.2  (прямоугольник+треугольник объединены в ОДИН
;                блок вместо двух независимых объектов, треугольник
;                растянут на всю высоту прямоугольника (широкая часть
;                = верхний край целиком, остриё = нижний край целиком,
;                без отступов) - Claude, 2026-07-22, по прямой правке
;                пользователя после показанного скриншота)
;   0.1  (первая версия - два отдельных объекта, неверные
;                пропорции треугольника - LEP-END.LSP, устарела)
;
;   НАЗНАЧЕНИЕ:
;   Символ КТП (наземная трансформаторная подстанция) - прямоугольник
;   (*LEP-KTP-Width* x *LEP-KTP-Height*, LEP-CONFIG.LSP) с треугольником-
;   значком трансформатора внутри. ТОТ ЖЕ ПРИНЦИП, что и у символа опоры
;   (LEP-POLESYM.LSP): блок создаётся ОДИН РАЗ через entmake (BLOCK/
;   LWPOLYLINE/SOLID/ENDBLK), дальше вставляется через entmake (INSERT) -
;   не через интерактивные "-BLOCK"/"-INSERT" (та же причина, что и у
;   опоры - надёжнее, нет риска нарваться на диалог/неверный порядок
;   промптов).
;
;   ⚠️ ФИКС 2026-07-22 (по прямой правке пользователя, после показа
;   скриншота реального КТП): ПЕРВАЯ версия рисовала прямоугольник и
;   треугольник как ДВА НЕЗАВИСИМЫХ объекта (не блок), и треугольник
;   был МЕЛКИМ, с отступами со всех сторон, не касаясь краёв
;   прямоугольника. Пользователь поправил на месте: (1) треугольник
;   должен ТЯНУТЬСЯ НА ВСЮ ВЫСОТУ - широкая часть точно у верхнего
;   края прямоугольника (от угла до угла), остриё точно у нижнего
;   края, без зазоров; (2) прямоугольник и треугольник должны быть
;   ОДНИМ объектом (блоком), не двумя разными - удобнее выделять/
;   двигать/привязывать констрейнтом. Оба пункта решены здесь разом -
;   блок вместо раздельных entmake, треугольник растянут на всю высоту.
;
;   Треугольник - ЗАЛИВКА ОДНИМ ЦВЕТОМ (SOLID), БЕЗ градиента (по
;   прямой просьбе пользователя, "оставим пока без градиента") - цвет
;   ФИКСИРОВАННЫЙ (*LEP-Color-KTP-Symbol*), не зависит от статуса
;   Проект/Сущ - тот же принцип, что и у серого креста символа опоры.
;
;   ⚠️ Блок, как и символ опоры, создаётся ТОЛЬКО ЕСЛИ ЕЩЁ НЕ
;   СУЩЕСТВУЕТ - не передефайнится при повторной загрузке (см.
;   подробное обоснование этого решения в LEP-POLESYM.LSP, тот же
;   принцип). Если понадобится поправить геометрию после того, как на
;   чертеже уже есть вставленные КТП - см. README, раздел про символ
;   опоры (там же общее решение этой проблемы).
;
;=====================================================================

(setq *LEP-Block-Ktp* "LEP-KTP-SYM")


;=====================================================================
; LEP:CreateKtpSymbolBlock
;
; Создаёт блок-символ КТП (*LEP-Block-Ktp*) - прямоугольник + залитый
; треугольник, см. шапку файла. Точка вставки блока (0,0,0) -
; геометрический центр прямоугольника (тот же принцип, что и у символа
; опоры).
;=====================================================================

(defun LEP:CreateKtpSymbolBlock (/ HalfW HalfH RectVerts RectList TriLeft TriRight TriBottom V)

    (if (not (tblsearch "BLOCK" *LEP-Block-Ktp*))
        (progn
            (setq HalfW (/ *LEP-KTP-Width* 2.0))
            (setq HalfH (/ *LEP-KTP-Height* 2.0))

            (entmake
                (list
                    (cons 0 "BLOCK")
                    (cons 2 *LEP-Block-Ktp*)
                    (cons 70 0)
                    (cons 10 (list 0.0 0.0 0.0))
                    (cons 8 "0")
                )
            )

            ;; Прямоугольник - закрытая LWPOLYLINE, LWEIGHT/цвет ByBlock
            ;; (наследуются от INSERT - тот же приём, что у трапеции
            ;; опоры в LEP-POLESYM.LSP).
            (setq RectVerts
                (list
                    (list (- HalfW) (- HalfH))
                    (list HalfW (- HalfH))
                    (list HalfW HalfH)
                    (list (- HalfW) HalfH)
                )
            )
            (setq RectList
                (list
                    '(0 . "LWPOLYLINE")
                    '(100 . "AcDbEntity")
                    (cons 8 "0")
                    (cons 370 -2)
                    '(100 . "AcDbPolyline")
                    (cons 90 (length RectVerts))
                    '(70 . 1)
                )
            )
            (foreach V RectVerts
                (setq RectList (append RectList (list (cons 10 V))))
            )
            (entmake RectList)

            ;; Треугольник - вершиной ВНИЗ, растянут на ВСЮ высоту
            ;; прямоугольника (широкая часть = верхние два угла целиком,
            ;; остриё = центр нижнего края целиком, БЕЗ отступов - см.
            ;; ⚠️ ФИКС 2026-07-22 в шапке файла). Заливка SOLID, ОДНИМ
            ;; цветом (*LEP-Color-KTP-Symbol*, фиксированный - группа
            ;; DXF 62, не ByBlock/ByLayer, тот же принцип, что у креста
            ;; опоры). Для ТРЕУГОЛЬНИКА (3 разные точки, 4-я группа -
            ;; повторение 3-й) порядок вершин не критичен так, как для
            ;; четырёхугольника (см. README про "заливку символа опоры") -
            ;; самопересечение ("бабочка") на трёх точках невозможно
            ;; геометрически.
            (setq TriLeft   (list (- HalfW) HalfH))
            (setq TriRight  (list HalfW HalfH))
            (setq TriBottom (list 0.0 (- HalfH)))

            (entmake
                (list
                    '(0 . "SOLID")
                    (cons 8 "0")
                    (cons 62 *LEP-Color-KTP-Symbol*)
                    (cons 10 TriLeft)
                    (cons 11 TriRight)
                    (cons 12 TriBottom)
                    (cons 13 TriBottom)
                )
            )

            (entmake (list (cons 0 "ENDBLK") (cons 8 "0")))

            (princ (strcat "\n[LEP-KTPSYM] Создан блок-символ КТП: " *LEP-Block-Ktp*))
        )
    )
)


;=====================================================================
; LEP:InsertKtpSymbol
;
; Вставляет символ КТП (блок целиком - прямоугольник+треугольник) в
; точку Point, слой - по статусу (*LEP-Layer-Proj-TP*/
; *LEP-Layer-Exist-TP*, уже существовали в проекте, но простаивали до
; появления КТП). Без разворота (КТП не привязана к направлению
; маршрута, в отличие от символа опоры) - группа 50 всегда 0.
;
; Возвращает ename вставленного блока - используется вызывающей
; стороной (LEP-END.LSP) для GEOMCONSTRAINT и XDATA (LEP:AddKtpData).
;=====================================================================

(defun LEP:InsertKtpSymbol (Point Status / Layer)

    (if (= Status "EXIST")
        (setq Layer *LEP-Layer-Exist-TP*)
        (setq Layer *LEP-Layer-Proj-TP*)
    )

    (entmake
        (list
            '(0 . "INSERT")
            (cons 8 Layer)
            (cons 2 *LEP-Block-Ktp*)
            (cons 10 (list (car Point) (cadr Point) 0.0))
            (cons 41 1.0)
            (cons 42 1.0)
            (cons 43 1.0)
            (cons 50 0.0)
        )
    )

    ;; ✅ ДОБАВЛЕНО 2026-07-22 (по прямому замечанию пользователя):
    ;; толщина линии по статусу (Проект. жирнее Сущ.) - тот же приём и
    ;; те же константы (*LEP-LWeight-Proj*/*LEP-LWeight-Exist*), что и
    ;; у символа опоры (LEP:InsertPoleSymbol, LEP-POLESYM.LSP).
    ;; Прямоугольник внутри блока уже имеет LWEIGHT=ByBlock (группа 370
    ;; = -2, см. LEP:CreateKtpSymbolBlock выше) - именно поэтому
    ;; значение, выставленное здесь на самом INSERT, "протекает" на его
    ;; геометрию, тот же механизм, что и у трапеции опоры.
    (if (= Status "EXIST")
        (LEP:SetEntityLWeight (entlast) *LEP-LWeight-Exist*)
        (LEP:SetEntityLWeight (entlast) *LEP-LWeight-Proj*)
    )

    (entlast)
)


(princ "\nLEP-KTPSYM v0.3 загружен (символ КТП - блок с толщиной линии по статусу).")
(princ)
