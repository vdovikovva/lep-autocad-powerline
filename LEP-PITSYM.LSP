;=====================================================================
;
;   ПРОЕКТ:      LEP
;   ФАЙЛ:        LEP-PITSYM.LSP
;   ВЕРСИЯ:      0.1  (первая версия - Claude, 2026-08-11)
;
;   НАЗНАЧЕНИЕ:
;   Символ КОТЛОВАНА ГНБ (*LEP-Pit-Length* x *LEP-Pit-Width*,
;   LEP-CONFIG.LSP) - простой прямоугольник, как у кабельного киоска.
;   Ставится автоматически на обоих концах каждого проектируемого
;   пролёта КЛ, проложенного ГНБ (см. LEP:PlaceGnbPits в LEP-SPAN.LSP).
;
;   ЗАЧЕМ (требование пользователя 2026-08-11): у любого ГНБ-прокола в
;   реальности всегда есть рабочий котлован (стоит буровая установка) и
;   приёмный (выходит бур). До этого их рисовали вручную на каждом
;   чертеже.
;
;   УСТРОЕН ПО ОБРАЗЦУ LEP-KKSYM.LSP: блок создаётся ОДИН РАЗ через
;   entmake (BLOCK/LWPOLYLINE/ENDBLK), вставляется через entmake
;   (INSERT) - не интерактивными "-BLOCK"/"-INSERT" (см. правило про
;   `command` в CLAUDE.md).
;
;   ⚠️ ОТЛИЧИЕ ОТ КИОСКА И КТП - РАЗВОРОТ. Котлован копают ВДОЛЬ оси
;   прокола, поэтому у него, как у символа опоры, есть угол поворота
;   (группа DXF 50 при вставке). Длинная сторона (*LEP-Pit-Length*)
;   лежит вдоль оси X блока - значит угол, переданный в
;   LEP:InsertPitSymbol, это ПРЯМО азимут прокола, без поправки на 90°.
;   ⚠️ Именно на такой поправке уже обжигались в LEP-END.LSP (опоры МТП
;   уезжали перпендикулярно трассе) - здесь её нет СОЗНАТЕЛЬНО, потому
;   что геометрия блока изначально нарисована "лёжа".
;
;   ⚠️ ЦВЕТ ЗАДАН ПРЯМО В ГЕОМЕТРИИ (группа DXF 62), а не ByLayer - тот
;   же приём, что у серого креста опоры и у маркера смены прокладки:
;   котлован всегда синий, от статуса Проект./Сущ. он не зависит (котлован
;   бывает только проектируемым - существующий никто не показывает).
;
;   ⚠️ ТОЛЩИНА ЛИНИИ - ByBlock в геометрии (370 = -2), реальное значение
;   выставляется на INSERT снаружи, как у киоска. Это позволяет менять
;   её одной константой, не трогая уже созданный в чертеже блок.
;
;   ⚠️ Блок, как и остальные символы проекта, создаётся ТОЛЬКО ЕСЛИ ЕГО
;   ЕЩЁ НЕТ - НЕ передефайнится при повторной загрузке. Поменяете размер
;   в LEP-CONFIG.LSP - на чертежах, где котлованы уже стоят, блок
;   придётся удалить вручную, иначе правка не проявится (подробное
;   обоснование - в LEP-POLESYM.LSP).
;
;=====================================================================

(setq *LEP-Block-Pit* "LEP-PIT-SYM")


;=====================================================================
; LEP:CreatePitSymbolBlock
;
; Создаёт блок-символ котлована (*LEP-Block-Pit*) - один замкнутый
; прямоугольник. Точка вставки блока (0,0,0) - геометрический ЦЕНТР
; прямоугольника (тот же принцип, что у символов опоры, КТП и киоска:
; вызывающая сторона всегда думает о центре, а не об угле).
;
; Длина (*LEP-Pit-Length*) откладывается по оси X блока, ширина
; (*LEP-Pit-Width*) - по оси Y. Благодаря этому разворот блока при
; вставке совпадает с азимутом прокола один в один.
;=====================================================================

(defun LEP:CreatePitSymbolBlock (/ HalfL HalfW RectVerts RectList V)

    (if (not (tblsearch "BLOCK" *LEP-Block-Pit*))
        (progn
            (setq HalfL (/ *LEP-Pit-Length* 2.0))
            (setq HalfW (/ *LEP-Pit-Width* 2.0))

            (entmake
                (list
                    (cons 0 "BLOCK")
                    (cons 2 *LEP-Block-Pit*)
                    (cons 70 0)
                    (cons 10 (list 0.0 0.0 0.0))
                    (cons 8 "0")
                )
            )

            ;; Прямоугольник - закрытая LWPOLYLINE (группа 70 = 1).
            ;; Порядок вершин - по периметру (левый-нижний -> правый-нижний
            ;; -> правый-верхний -> левый-верхний): для замкнутой полилинии
            ;; это правильный обход, в отличие от заливки SOLID, где
            ;; порядок другой (1-2-4-3, см. заметку в CLAUDE.md).
            (setq RectVerts
                (list
                    (list (- HalfL) (- HalfW))
                    (list HalfL (- HalfW))
                    (list HalfL HalfW)
                    (list (- HalfL) HalfW)
                )
            )
            (setq RectList
                (list
                    '(0 . "LWPOLYLINE")
                    '(100 . "AcDbEntity")
                    (cons 8 "0")
                    (cons 62 *LEP-Color-Pit*)   ; цвет - жёстко в геометрии, не ByLayer
                    (cons 370 -2)               ; толщина - ByBlock, задаётся на INSERT
                    '(100 . "AcDbPolyline")
                    (cons 90 (length RectVerts))
                    '(70 . 1)
                )
            )
            (foreach V RectVerts
                (setq RectList (append RectList (list (cons 10 V))))
            )
            (entmake RectList)

            (entmake (list (cons 0 "ENDBLK") (cons 8 "0")))

            (princ (strcat "\n[LEP-PITSYM] Создан блок-символ котлована ГНБ: " *LEP-Block-Pit*))
        )
    )
)


;=====================================================================
; LEP:InsertPitSymbol
;
; Вставляет символ котлована ЦЕНТРОМ в точку Point с разворотом RotAngle
; (РАДИАНЫ, азимут оси прокола - длинная сторона ляжет вдоль него).
;
; Слой ВСЕГДА ОДИН - *LEP-Layer-Pit*, независимо от статуса: котлован
; бывает только проектируемым, "существующих котлованов" на плане не
; показывают. Толщина линии - общая проектная (*LEP-LWeight-Proj*), по
; прямому уточнению пользователя: котлован чертится той же толщиной,
; что и все остальные проектируемые объекты.
;
; Возвращает ename вставленного блока - вызывающая сторона
; (LEP:PlacePitAtNode в LEP-SPAN.LSP) вешает на него XDATA.
;=====================================================================

;; ⚠️ 2026-08-18: параметр переименован Angle -> RotAngle. Angle - имя
;; ВСТРОЕННОЙ функции AutoLISP, а параметры/локальные в AutoLISP видны
;; и во всех вызываемых отсюда функциях (динамическая видимость): пока
;; работает эта функция, (angle ...) в любой из них упал бы с "bad
;; function". Здесь до выстрела дело не дошло (никто ниже угол не
;; считает), но ровно на таком имени 2026-08-18 поймали потерю XDATA у
;; ПУ - разбор в шапке LEP:AddEquipToExistingPole (LEP-DATA.LSP).
(defun LEP:InsertPitSymbol (Point RotAngle)

    (entmake
        (list
            '(0 . "INSERT")
            (cons 8 *LEP-Layer-Pit*)
            (cons 2 *LEP-Block-Pit*)
            (cons 10 (list (car Point) (cadr Point) 0.0))
            (cons 41 1.0)
            (cons 42 1.0)
            (cons 43 1.0)
            (cons 50 RotAngle)
        )
    )

    ;; Работает именно потому, что прямоугольник внутри блока имеет
    ;; LWEIGHT = ByBlock (см. LEP:CreatePitSymbolBlock выше).
    (LEP:SetEntityLWeight (entlast) *LEP-LWeight-Proj*)

    (entlast)
)


(princ "\nLEP-PITSYM v0.1 загружен (символ котлована ГНБ - прямоугольник вдоль оси прокола).")
(princ)
