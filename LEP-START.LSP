;=====================================================================
;
;   ПРОЕКТ:      LEP
;   ФАЙЛ:        LEP-START.LSP
;   ВЕРСИЯ:      0.7  (добавлен модуль LEP-KTPSYM.LSP - символ КТП,
;                автосоздание блока при загрузке - Claude, 2026-07-22)
;   0.6  (добавлен модуль LEP-GEOPOINTS.LSP - GPS-точки из
;                GeoJSON -> зелёные кружки-ориентиры - Claude, 2026-07-20)
;   0.5  (TRUSTEDPATHS больше не зависит от папки DWG -
;                Support File Search Path подтверждён живым тестом,
;                Claude, 2026-07-16)
;   0.4  (испр. Claude)
;
;   ИСПРАВЛЕНО В ЭТОЙ ВЕРСИИ:
;   В списке загрузки не хватало ДВУХ файлов, которые реально
;   существуют на диске, но никогда не подключались:
;     - LEP-DATA.LSP   (там LEP:SetData/GetData/AddRoute и т.д. -
;                        на них держится вся передача данных между
;                        маршрутом, опорами и будущей ведомостью)
;     - LEP-ROUTE.LSP  (там C:LEP-ROUTE - команда черчения трассы,
;                        именно её вам и не хватило)
;   Из-за этого LEP-ROUTE была "невидимой" командой, а LEP-POLE
;   в свою очередь всё равно упала бы следующей, т.к. вызывает
;   функции из LEP-DATA.LSP, которых не было в памяти.
;
;   ⚠️ ФИКС 2026-07-16: раньше попытка через Support File Search Path
;   не срабатывала (причина так и не была найдена) - обходились тем,
;   что findfile заодно смотрит и в папку ТЕКУЩЕГО ЧЕРТЕЖА, поэтому
;   DWG держали рядом с модулями. Теперь Support Path подтверждён
;   живым тестом (2026-07-16, findfile нашёл файл модуля из чертежа,
;   сохранённого в ДРУГОЙ папке) - DWG может лежать где угодно, см.
;   CLAUDE.md, раздел про правило хранения файлов (снято).
;
;   НАЗНАЧЕНИЕ:
;   Главный загрузчик проекта LEP. Загружается АВТОМАТИЧЕСКИ при
;   открытии любого чертежа (см. acaddoc.lsp, добавлен 2026-07-16),
;   либо вручную через APPLOAD/(load "LEP-START.LSP") - например, для
;   перезагрузки кода после правок без переоткрытия чертежа. Все
;   остальные модули подключаются автоматически.
;
;=====================================================================
 
 
;=====================================================================
;
;   АВТОРЕГИСТРАЦИЯ ПАПКИ КАК ДОВЕРЕННОЙ (TRUSTEDPATHS)
;
;   Без этого AutoCAD спрашивает подтверждение на КАЖДЫЙ отдельный
;   файл LEP-*.LSP при загрузке (это его система безопасности,
;   SECURELOAD/TRUSTEDPATHS, а не наш баг). Регистрируем папку один
;   раз здесь - дальше все вложенные load внутри LEP:LoadFile пойдут
;   уже тихо.
;
;   ⚠️ ФИКС 2026-07-16 (просьба пользователя - DWG в одной папке с
;   модулями превращал эту папку в склад чужих чертежей): раньше путь
;   брался из (getvar "DWGPREFIX") - папки ТЕКУЩЕГО ЧЕРТЕЖА, и поэтому
;   DWG ОБЯЗАН был физически лежать рядом с модулями LEP-*.LSP (иначе
;   и findfile их не находил, и TRUSTEDPATHS регистрировал не ту
;   папку). Теперь путь берётся через (findfile "LEP-START.LSP") -
;   СВОЯ СОБСТВЕННАЯ папка, а не папка чертежа - работает независимо
;   от того, где физически лежит DWG.
;
;   ⚠️ УСЛОВИЕ: папка с модулями LEP должна быть добавлена в Support
;   File Search Path (Options -> Files -> Support File Search Path) -
;   иначе (findfile "LEP-START.LSP") тоже вернёт nil, ничего не
;   заработает, ниже будет явное предупреждение. Это разовая настройка
;   на КОМПЬЮТЕР (не на чертёж) - у каждого пользователя (вы на Mac,
;   коллега на Windows) она делается один раз и дальше не трогается,
;   независимо от того, сколько разных DWG и в каких папках открывается.
;   Подтверждено живым тестом 2026-07-16: (findfile "LEP-CONFIG.LSP")
;   из чертежа, сохранённого В ДРУГОЙ папке, нашёл файл корректно.
;
;   Побочный положительный эффект: несохранённый (совсем новый) чертёж
;   раньше не мог определить путь (DWGPREFIX у него пустой) - теперь
;   это больше не проблема, путь не зависит от состояния сохранения
;   чертежа вообще.
;
;=====================================================================

(setq *LEP-TrustPath* (vl-filename-directory (findfile "LEP-START.LSP")))

(if (not *LEP-TrustPath*)
    (princ "\n[LEP-START] ВНИМАНИЕ: не могу определить свою папку через findfile - убедитесь, что папка с модулями LEP добавлена в Support File Search Path (Options -> Files -> Support File Search Path).")
    (progn
        (if (getvar "TRUSTEDPATHS")
            (setq LEP-CurTrusted (getvar "TRUSTEDPATHS"))
            (setq LEP-CurTrusted "")
        )

        (if (not (wcmatch LEP-CurTrusted (strcat "*" *LEP-TrustPath* "*")))
            (setvar "TRUSTEDPATHS"
                (strcat
                    LEP-CurTrusted
                    (if (= LEP-CurTrusted "") "" ";")
                    *LEP-TrustPath*
                )
            )
        )
    )
)
 
 
(defun LEP:LoadFile (FileName / FullPath)
 
    (setq FullPath (findfile FileName))
 
    (if FullPath
        (progn
            (load FullPath)
            (princ (strcat "\nЗагружен: " FileName))
        )
        (princ
            (strcat
                "\nНЕ НАЙДЕН: " FileName
                "  -- проверьте, что папка с модулями LEP добавлена в"
                " Support File Search Path (Options -> Files)."
            )
        )
    )
 
)
 
 
;=====================================================================
;
; ЗАПУСК ЗАГРУЗКИ
;
; ПОРЯДОК ВАЖЕН! Каждый следующий модуль может использовать функции
; из предыдущих.
;
; 1. CONFIG      настройки
; 2. UTILS       общие функции
; 3. DATA        хранение данных объектов (XDATA) -- ДОБАВЛЕНО
; 4. SETUP       подготовка чертежа (слои и т.д.)
; 5. POLYLINE    общие функции работы с полилиниями (вершины и т.д.)
; 6. POLESYM     символ опоры (трапеция+крест) -- ДОБАВЛЕНО
; 7. ROUTE       команда черчения трассы ЛЭП -- ДОБАВЛЕНО
; 8. POLE        установка опор на трассу
; 9. SPAN        работа с пролётами
; 10. SCALE      установка масштаба подложки
; 11. REPORT     ведомость опор, кабелей и проводов
; 12. END        оконечное оборудование маршрута (МТП/ПУ) -- ДОБАВЛЕНО
;                (грузится ПОСЛЕ POLE - использует его функции)
; 13. GEOPOINTS  GPS-точки из GeoJSON -> зелёные кружки-ориентиры --
;                ДОБАВЛЕНО 2026-07-20
; 14. KTPSYM     символ КТП (прямоугольник+треугольник) -- ДОБАВЛЕНО
;                2026-07-22 (грузится ПЕРЕД END - использует его
;                функции)
; 15. KKSYM      символ кабельного киоска (прямоугольник) -- ДОБАВЛЕНО
;                2026-07-24 (тоже ПЕРЕД END, по той же причине)
; 16. TRANSSYM   символ точки смены способа прокладки (непечатаемый
;                кружок) -- ДОБАВЛЕНО 2026-07-24 (тоже ПЕРЕД END)
; 17. PITSYM     символ котлована ГНБ (прямоугольник вдоль оси прокола)
;                -- ДОБАВЛЕНО 2026-08-11. Грузится ПЕРЕД SPAN: котлованы
;                ставит сам LEP-SPAN на концах ГНБ-проколов, отдельной
;                команды у них нет
;
;=====================================================================


(princ "\n")
(princ "======================================")
(princ "\n Загрузка системы LEP")
(princ "\n======================================")

(LEP:LoadFile "LEP-CONFIG.LSP")
(LEP:LoadFile "LEP-UTILS.LSP")
(LEP:LoadFile "LEP-DATA.LSP")
(LEP:LoadFile "LEP-SETUP.LSP")
(LEP:LoadFile "LEP-POLYLINE.LSP")
(LEP:LoadFile "LEP-POLESYM.LSP")
(LEP:LoadFile "LEP-KTPSYM.LSP")
(LEP:LoadFile "LEP-KKSYM.LSP")
(LEP:LoadFile "LEP-TRANSSYM.LSP")
(LEP:LoadFile "LEP-PITSYM.LSP")
(LEP:LoadFile "LEP-ROUTE.LSP")
(LEP:LoadFile "LEP-POLE.LSP")
(LEP:LoadFile "LEP-SPAN.LSP")
(LEP:LoadFile "LEP-SCALE.LSP")
(LEP:LoadFile "LEP-REPORT.LSP")
(LEP:LoadFile "LEP-END.LSP")
(LEP:LoadFile "LEP-GEOPOINTS.LSP")


;=====================================================================
;
; АВТОЗАПУСК LEP-SETUP
;
; Раньше пользователь запускал LEP-SETUP вручную первым шагом после
; APPLOAD. Убрано из ручных шагов - слои нужны ВСЕГДА, и одна лишняя
; команда, которую легко забыть, не даёт никакой пользы: LEP:CreateLayer
; сам ничего не делает повторно, если слой уже существует (см.
; LEP-SETUP.LSP), поэтому безопасно вызывать её при каждой загрузке
; чертежа. Команда C:LEP-SETUP как таковая никуда не делась (её всё
; ещё можно вызвать вручную из командной строки, если когда-нибудь
; понадобится, например слой случайно удалили) - просто больше не
; рекламируется в списке команд ниже и не нужна для обычной работы.
;
;=====================================================================

(C:LEP-SETUP)


;=====================================================================
;
; АВТОСОЗДАНИЕ СИМВОЛА ОПОРЫ
;
; Тот же принцип, что и у LEP-SETUP выше - блок-символ опоры
; (трапеция+крест, *LEP-Block-Pole* в CONFIG) нужен ВСЕГДА, поэтому
; создаётся автоматически при каждой загрузке, а не отдельной ручной
; командой. LEP:CreatePoleSymbolBlock сама ничего не делает повторно,
; если блок уже есть в чертеже (см. LEP-POLESYM.LSP - там же и
; объяснение, почему НЕ "передефайнится" каждый раз, в отличие от
; слоёв).
;
;=====================================================================

(LEP:CreatePoleSymbolBlock)

;; Тот же принцип - блок-символ КТП (прямоугольник+треугольник,
;; LEP-KTPSYM.LSP, *LEP-Block-Ktp* в CONFIG) нужен ВСЕГДА, создаётся
;; автоматически, сама ничего не делает повторно, если блок уже есть.
(LEP:CreateKtpSymbolBlock)

;; То же самое для блока-символа кабельного киоска (простой
;; прямоугольник, LEP-KKSYM.LSP, *LEP-Block-Kk* в CONFIG) - добавлен
;; 2026-07-24 вместе с самим киоском.
(LEP:CreateKkSymbolBlock)

;; И для маркера смены способа прокладки (непечатаемый кружок,
;; LEP-TRANSSYM.LSP, *LEP-Block-Trans* в CONFIG) - добавлен 2026-07-24.
(LEP:CreateTransSymbolBlock)

;; И для котлована ГНБ (прямоугольник, LEP-PITSYM.LSP, *LEP-Block-Pit* в
;; CONFIG) - добавлен 2026-08-11. Отдельной команды у котлованов нет: их
;; ставит сам LEP-SPAN на концах каждого ГНБ-прокола, поэтому блок должен
;; существовать к моменту первого же пролёта.
(LEP:CreatePitSymbolBlock)

(princ "\n")
(princ "======================================")
(princ "\n LEP загружен успешно")
(princ "\n Команды:")
(princ "\n LEP-ROUTE")
(princ "\n LEP-ROUTEVIS")
(princ "\n LEP-POLE")
(princ "\n LEP-POLE-ALONE")
(princ "\n LEP-POLE-DELETE")
(princ "\n LEP-POLE-MOVE")
(princ "\n LEP-END")
(princ "\n LEP-SPAN")
(princ "\n LEP-SPAN-REPAIR")
(princ "\n LEP-SCALE")
(princ "\n LEP-REPORT")
(princ "\n LEP-GEOPOINTS-EXTRACT")
(princ "\n LEP-GEOPOINTS-DRAW")
(princ "\n LEP-GEOPOINTS-CLEAR")
(princ "\n======================================")
 
(princ)
