;=====================================================================
;
;   ПРОЕКТ:      LEP
;   ФАЙЛ:        LEP-POLESYM.LSP
;   ВЕРСИЯ:      0.3  (честные имена углов в InsertPoleGroup, картинка
;                не изменилась - аудит Claude Fable, 2026-07-11)
;
;   НАЗНАЧЕНИЕ:
;   Символ опоры на плане (трапеция + крест, см. LEP-CONFIG.LSP) -
;   создание блока-заготовки и вставка одной/нескольких трапеций
;   (главная опора + откос(ы)) с нужным разворотом и толщиной линии.
;   ЗАМЕНЯЕТ test-block (старая заглушка-кружок) - настоящий рабочий
;   символ. Файл LEP-MAKETESTBLOCK.LSP, который её создавал, удалён из
;   проекта 2026-07-10 (полностью не нужен - см. историю git).
;
;   ГЕОМЕТРИЯ БЛОКА создаётся ЧЕРЕЗ entmake (BLOCK/LWPOLYLINE/LINE/
;   ENDBLK), не через интерактивную команду "-BLOCK" - так надёжнее
;   (нет риска нарваться на диалоговое окно/неверный порядок промптов,
;   та же причина, по которой в проекте уже несколько раз горели на
;   command: LEADER, -linetype). По этой же причине блок СОЗДАЁТСЯ,
;   ТОЛЬКО ЕСЛИ ЕЩЁ НЕ СУЩЕСТВУЕТ (как слои в LEP-SETUP.LSP), а не
;   передефайнится каждую загрузку - для честного "redefine" нужно
;   было бы либо гонять "-BLOCK" с подтверждением перезаписи (не
;   проверено вживую в консоли AutoCAD - в этой среде консоли нет),
;   либо городить более сложный механизм замены геометрии у блока с
;   уже существующими ссылками (вставленными опорами). Если после
;   визуальной проверки геометрию трапеции понадобится поменять -
;   нужно будет либо один раз вручную удалить блок из чертежа (пока
;   на чертеже нет ни одной опоры), либо протестировать передефайн
;   вживую и добавить сюда отдельно.
;
;   ВСТАВКА блока - тоже через entmake (INSERT), а НЕ через
;   "-INSERT" - блок без атрибутов (в отличие от старого test-block с
;   атрибутом TIP), поэтому ATTREQ не нужен, а entmake даёт угол
;   поворота СТРОГО В РАДИАНАХ независимо от системной переменной
;   AUNITS чертежа - через "command" пришлось бы гадать, в каких
;   единицах команда ждёт число (учитывая уже не раз пойманные баги
;   на порядке/формате аргументов command, решили не рисковать).
;
;=====================================================================



;=====================================================================
; LEP:GetPoleColumns
;
; Сколько трапеций (столбов) рисовать для данного типа опоры.
;
; ⚠️ ИЗМЕНЕНО 2026-08-03: число берётся из *LEP-PoleStands*
; (LEP-CONFIG.LSP) - того же справочника, из которого ведомость берёт
; количество железобетонных стоек. Раньше был отдельный список
; *LEP-PoleColumns*, он удалён.
;
; Почему это правильно, а не "склеили что попало": откос на чертеже -
; это и есть вторая (третья) СТОЙКА опоры, просто вкопанная под углом.
; Число трапеций и число стоек - одна и та же величина по смыслу, и
; хранить её в двух списках означало бы однажды поправить один и
; забыть другой: на чертеже опора с откосом, в ведомости одна стойка,
; и никаких признаков ошибки.
;
; Формат строки справочника - ("тип" "марка стойки" количество),
; отсюда caddr.
;
; Если тип не найден (опечатка или новый тип, забыли внести) - тихо
; считает 1 и рисует одиночную опору, а не падает с ошибкой: чертёж
; при этом хоть и неточен, но работать можно. ⚠️ В ВЕДОМОСТИ такой же
; случай, наоборот, кричит отдельной строкой (ЭТАП 2, LEP-REPORT.LSP) -
; там тихий фолбэк означал бы потерянный материал.
;=====================================================================

(defun LEP:GetPoleColumns (PoleType / Found)
    (setq Found (assoc PoleType *LEP-PoleStands*))
    (if Found
        (caddr Found)
        1
    )
)



;=====================================================================
; LEP:CreatePoleSymbolBlock
;
; Создаёт блок-символ опоры (*LEP-Block-Pole* в CONFIG) - трапеция +
; крест, см. размеры в LEP-CONFIG.LSP. Точка вставки блока (0,0,0) -
; геометрический центр (там же, где пересекается крест).
;
; Трапеция и обе линии креста внутри блока получают LWEIGHT = ByBlock
; (группа DXF 370 = -2) - это ключевое условие для того, чтобы толщина
; линии по статусу (Проект./Сущ., см. LEP:InsertPoleSymbol ниже)
; реально работала: значение LWEIGHT, выставленное на самом INSERT,
; "протекает" на вложенную графику ТОЛЬКО если у неё самой LWEIGHT
; = ByBlock, а не какое-то конкретное число.
;=====================================================================

(defun LEP:CreatePoleSymbolBlock (/ HalfBase HalfTop HalfHeight HalfCross Verts TrapList V)

    (if (not (tblsearch "BLOCK" *LEP-Block-Pole*))
        (progn
            (setq HalfBase   (/ *LEP-Pole-Sym-Base* 2.0))
            (setq HalfTop    (/ *LEP-Pole-Sym-Top* 2.0))
            (setq HalfHeight (/ *LEP-Pole-Sym-Height* 2.0))
            (setq HalfCross  (/ *LEP-Pole-Sym-Cross* 2.0))

            ;; Вершины трапеции - широкая сторона внизу (локальный -Y,
            ;; "к началу маршрута"), узкая вверху (локальный +Y, "к
            ;; концу маршрута"), см. LEP:GetPoleRotation ниже про то,
            ;; как это совмещается с реальным направлением трассы.
            (setq Verts
                (list
                    (list (- HalfBase) (- HalfHeight))
                    (list HalfBase (- HalfHeight))
                    (list HalfTop HalfHeight)
                    (list (- HalfTop) HalfHeight)
                )
            )

            (entmake
                (list
                    (cons 0 "BLOCK")
                    (cons 2 *LEP-Block-Pole*)
                    (cons 70 0)
                    (cons 10 (list 0.0 0.0 0.0))
                    (cons 8 "0")
                )
            )

            ;; Трапеция - закрытая LWPOLYLINE (флаг 70 = 1). Формат
            ;; entmake для LWPOLYLINE - тот же, что уже проверен и
            ;; работает в LEP:CreateSpanEntity (LEP-SPAN.LSP).
            (setq TrapList
                (list
                    '(0 . "LWPOLYLINE")
                    '(100 . "AcDbEntity")
                    (cons 8 "0")
                    (cons 370 -2)
                    '(100 . "AcDbPolyline")
                    (cons 90 (length Verts))
                    '(70 . 1)
                )
            )
            (foreach V Verts
                (setq TrapList (append TrapList (list (cons 10 V))))
            )
            (entmake TrapList)

            ;; Крест - две ОТДЕЛЬНЫЕ линии (не полилиния - крест не
            ;; единый непрерывный путь), через центр (0,0), каждая
            ;; целиком длиной *LEP-Pole-Sym-Cross*. Цвет - ФИКСИРОВАННО
            ;; серый (группа DXF 62 = *LEP-Color-PoleCross*), а не
            ;; ByBlock/ByLayer - по просьбе пользователя крест не должен
            ;; менять цвет вместе со статусом/цветом самой опоры
            ;; (2026-07-10). Толщина (370) при этом ОСТАЁТСЯ ByBlock -
            ;; крест по-прежнему становится жирнее/тоньше вместе с
            ;; остальной геометрией опоры по статусу Проект./Сущ.
            (entmake
                (list
                    '(0 . "LINE")
                    (cons 8 "0")
                    (cons 62 *LEP-Color-PoleCross*)
                    (cons 370 -2)
                    (cons 10 (list (- HalfCross) 0.0 0.0))
                    (cons 11 (list HalfCross 0.0 0.0))
                )
            )

            (entmake
                (list
                    '(0 . "LINE")
                    (cons 8 "0")
                    (cons 62 *LEP-Color-PoleCross*)
                    (cons 370 -2)
                    (cons 10 (list 0.0 (- HalfCross) 0.0))
                    (cons 11 (list 0.0 HalfCross 0.0))
                )
            )

            (entmake (list (cons 0 "ENDBLK") (cons 8 "0")))

            (princ (strcat "\n[LEP-POLESYM] Создан блок-символ опоры: " *LEP-Block-Pole*))
        )
    )
)



;=====================================================================
; LEP:SetEntityLWeight
;
; Устанавливает толщину линии (LWEIGHT, группа DXF 370) у уже
; существующей сущности - тем же приёмом entmod/assoc/subst, что уже
; используется для флага печати слоя (LEP:SetLayerNoPlot,
; LEP-SETUP.LSP) - детерминированно, без риска нарваться на
; неправильный порядок промптов у command.
;=====================================================================

(defun LEP:SetEntityLWeight (Ent Value / EData)
    (setq EData (entget Ent))
    (if (assoc 370 EData)
        (entmod (subst (cons 370 Value) (assoc 370 EData) EData))
        (entmod (append EData (list (cons 370 Value))))
    )
    (entupd Ent)
)



;=====================================================================
; LEP:GetPoleRotation
;
; Угол поворота символа опоры (в РАДИАНАХ - именно в них entmake
; ожидает группу 50 у INSERT, независимо от AUNITS чертежа) - широкая
; сторона трапеции (локальный -Y при повороте 0) должна смотреть к
; НАЧАЛУ маршрута, узкая (локальный +Y) - к КОНЦУ (по просьбе
; пользователя, 2026-07-10). Локальная "вперёд"-ось блока - +Y
; (90° от +X), поэтому чтобы совместить её с реальным направлением
; отрезка SegStart->SegEnd, поворот блока = угол этого отрезка - 90°.
;
; SegStart/SegEnd - точки СЕГМЕНТА трассы, на котором стоит опора (тот
; же отрезок, что уже находит LEP:FindNearestSegment в LEP-POLE.LSP) -
; направление считается "по трассе" локально, от предыдущей вершины
; к следующей, что для прямых участков и совпадает с общим
; направлением "от начала маршрута к концу".
;=====================================================================

(defun LEP:GetPoleRotation (SegStart SegEnd)
    (if (> (distance SegStart SegEnd) 1e-9)
        (- (angle SegStart SegEnd) (/ pi 2.0))
        0.0
    )
)



;=====================================================================
; LEP:InsertPoleSymbol
;
; Вставляет ОДНУ трапецию символа опоры в точку Point, с поворотом
; Rotation (радианы) и толщиной линии по статусу (Проект./Сущ., см.
; *LEP-LWeight-Proj*/*LEP-LWeight-Exist* в CONFIG). Слой берётся из
; ТЕКУЩЕГО CLAYER на момент вызова - переключать его должен вызывающий
; код (тот же порядок, что и у старого LEP:InsertPole).
;
; Через entmake, не через "-INSERT" - блок без атрибутов, поэтому
; ATTREQ не нужен, а группа 50 (поворот) у entmake всегда в радианах,
; без риска гадать про единицы измерения команды (см. шапку файла).
;
; Возвращает ename вставленного блока.
;=====================================================================

(defun LEP:InsertPoleSymbol (Point Rotation Status / LWeight)

    (entmake
        (list
            '(0 . "INSERT")
            (cons 8 (getvar "CLAYER"))
            (cons 2 *LEP-Block-Pole*)
            (cons 10 (list (car Point) (cadr Point) 0.0))
            (cons 41 1.0)
            (cons 42 1.0)
            (cons 43 1.0)
            (cons 50 Rotation)
        )
    )

    (if (= Status "EXIST")
        (setq LWeight *LEP-LWeight-Exist*)
        (setq LWeight *LEP-LWeight-Proj*)
    )
    (LEP:SetEntityLWeight (entlast) LWeight)

    (entlast)
)



;=====================================================================
; LEP:InsertPoleGroup
;
; Вставляет ГРУППУ трапеций опоры - главную + откос(ы), количество
; берётся из LEP:GetPoleColumns по типу опоры (1/2/3, см.
; *LEP-PoleStands* в CONFIG). Возвращает ename ГЛАВНОЙ трапеции -
; именно к ней привязываются XDATA/GEOMCONSTRAINT/подпись в LEP-POLE,
; откосы - чисто визуальные, без своих данных (это не "вторая опора"
; для ведомости, а конструктивная деталь одной и той же опоры).
;
; BlockRotation - угол ПОВОРОТА БЛОКА (радианы; = угол маршрута МИНУС
; 90°, см. LEP:GetPoleRotation выше) - именно его передают все
; вызывающие (LEP:InsertPole). Угол самого МАРШРУТА восстанавливается
; здесь обратной операцией (+90°) в RouteDir.
;
; ⚠️ ФИКС 2026-07-11 (аудит): раньше параметр назывался RouteAngle,
; хотя фактически сюда всегда приходил поворот БЛОКА - из-за этой
; путаницы старый комментарий утверждал, что откосы ставятся
; "перпендикулярно маршруту", а НА САМОМ ДЕЛЕ они ставились ВДОЛЬ
; маршрута (сзади главной опоры для 2-столбовых, сзади+спереди для
; 3-столбовых). Картинка на чертеже этим фиксом НЕ изменена (пользователь
; видел именно продольное размещение на тестах и не возражал) - фикс
; только приводит имена и комментарии в соответствие с реальностью,
; чтобы будущая правка угла легла в правильную систему координат.
;
; !! ЧЕРНОВОЕ ПРИБЛИЖЕНИЕ, ТРЕБУЕТ ПРОВЕРКИ !! Точный разворот откоса
; относительно главной опоры пользователь пока не уточнил (ждёт ответа
; от коллеги). Сейчас: откос(ы) на *LEP-Pole-Sym-Offset* м ВДОЛЬ оси
; маршрута, повёрнуты на 90° к главной трапеции. Когда появится точный
; угол - поправить ТОЛЬКО эту функцию, вставка/данные главной опоры
; не изменятся.
;=====================================================================

(defun LEP:InsertPoleGroup (Point BlockRotation PoleType Status / RouteDir Columns Pt2 Pt3 MainEnt)

    ;; Угол маршрута = поворот блока + 90° (см. LEP:GetPoleRotation -
    ;; там обратное вычитание). Все смещения откосов считаются от
    ;; НАСТОЯЩЕГО направления трассы, а не от поворота блока.
    (setq RouteDir (+ BlockRotation (/ pi 2.0)))

    (setq Columns (LEP:GetPoleColumns PoleType))
    (setq MainEnt (LEP:InsertPoleSymbol Point BlockRotation Status))

    ;; Откос 1 - ПОЗАДИ главной опоры по ходу маршрута (RouteDir + pi),
    ;; повёрнут на 90° от главной.
    (if (>= Columns 2)
        (progn
            (setq Pt2
                (list
                    (+ (car Point) (* *LEP-Pole-Sym-Offset* (cos (+ RouteDir pi))))
                    (+ (cadr Point) (* *LEP-Pole-Sym-Offset* (sin (+ RouteDir pi))))
                )
            )
            (LEP:InsertPoleSymbol Pt2 (+ BlockRotation (/ pi 2.0)) Status)
        )
    )

    ;; Откос 2 (только у 3-столбовых) - ВПЕРЕДИ по ходу маршрута
    ;; (RouteDir), повёрнут на -90° от главной.
    (if (>= Columns 3)
        (progn
            (setq Pt3
                (list
                    (+ (car Point) (* *LEP-Pole-Sym-Offset* (cos RouteDir)))
                    (+ (cadr Point) (* *LEP-Pole-Sym-Offset* (sin RouteDir)))
                )
            )
            (LEP:InsertPoleSymbol Pt3 (- BlockRotation (/ pi 2.0)) Status)
        )
    )

    MainEnt
)


(princ "\nLEP-POLESYM v0.3 загружен (символ опоры трапеция+крест).")
(princ)
