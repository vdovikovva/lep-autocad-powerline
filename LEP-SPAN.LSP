;=====================================================================
;
;   ПРОЕКТ:      LEP
;   ФАЙЛ:        LEP-SPAN.LSP
;   ВЕРСИЯ:      2.3  (2026-08-05: ПОСЕГМЕНТНЫЕ РАЗМЕРЫ ТЕПЕРЬ И У ВЛ
;                (было только у КЛ). Смысл правки не в самих размерах,
;                а в КОЛИЧЕСТВЕ КЛИКОВ: на длинной прямой ВЛ из
;                десятка опор больше не нужно обкликивать каждую пару -
;                можно кликнуть первую и последнюю опору, размер всё
;                равно появится между каждой парой соседних (у каждой
;                опоры своя вершина маршрута). Данные (марка, статус,
;                класс, длина) на таком участке и так одни и те же.
;                Переменная DimDistance удалена - стала не нужна.
;                Плюс ЗАЩИТА ОТ ТИХОЙ ПРИВЯЗКИ К ЧУЖОЙ ВЕРШИНЕ:
;                LEP:GetNearestVertexIndex брала ближайшую вершину
;                БЕЗ проверки расстояния, и пролёт мог молча уехать
;                концом на десятки метров - Claude)
;   2.2  (2026-08-04: У КЛ РАЗМЕРНАЯ ЛИНИЯ НА КАЖДОЕ
;                КОЛЕНО (новая LEP:CreateSpanDimensions) - траншея
;                "молнией" раньше получала один размер по прямой между
;                концами, то есть меньше, чем реально копают. Заодно
;                отпала нужда ставить маркер на каждом повороте: он
;                нужен был только чтобы колено стало своим пролётом.
;                МАРКЕР TRANS ТЕПЕРЬ РВЁТ ОБЪЕДИНЕНИЕ ТОЛЬКО У ГНБ -
;                траншея через него объединяется (прокол дискретен,
;                канава непрерывна). ⚠️ Посегментные размеры - ПОКА
;                ТОЛЬКО ДЛЯ КЛ, у ВЛ по-старому - Claude)
;   2.1  (2026-08-03: МАРКЕР ТОЧКИ РАЗРЫВА (TRANS) СТАЛ
;                ЖЁСТКОЙ ГРАНИЦЕЙ - LEP:GetSpanNeighbors не ищет
;                соседей через него, подписи через маркер не
;                объединяются НИКОГДА. До этого два прокола ГНБ под
;                разными углами, разделённые маркером, слипались в одну
;                подпись: марка/статус/способ у них совпадают, разные
;                они физикой, а не данными - Claude)
;   2.0  (2026-07-24: КОНЦОМ ПРОЛЁТА МОЖЕТ БЫТЬ НЕ ТОЛЬКО
;                ОПОРА - LEP:PickPole принимает КТП и кабельный киоск
;                (TYPE POLE/KTP/KK). Запас КЛ на концевые заделки стал
;                ПОКОНЦОВЫМ (LEP:GetEndReserve: опора 3 м, наземные
;                КТП/КК - 0 м), готовое число пишется в XDATA пролёта
;                (ключ RESERVE). ФИКС: параллельные близнецы (два
;                кабеля/провода между ОДНОЙ парой концов) больше НЕ
;                сливаются в одну подпись с суммой длин - Claude)
;   1.9  (2026-07-24: ЧЕРТЁЖ И ВЕДОМОСТЬ ОКОНЧАТЕЛЬНО
;                РАЗВЕДЕНЫ - на чертеже только физика (провод сырой,
;                кабель + 6 м на подъём), ВСЕ запасы и множитель фаз
;                видны только в ведомости. Новая LEP:GetDisplayLength,
;                подпись больше не смотрит в XDATA LENGTH вообще -
;                Claude)
;   1.8  (2026-07-24: НОВЫЕ НОРМЫ ЗАПАСА ДЛИНЫ -
;                LEP:GetRealLength переписана под общую формулу
;                "(база + фикс.добавка) x (1 + процент) x число_фаз":
;                ВЛ 4,5% (было 2%), КЛ ГНБ 2% и КЛ траншея 4% ПОВЕРХ
;                прежних +6 м на подъём на опору, провод 10/6 кВ
;                умножается на 3 (три фазы, СИП-3 - отдельный провод
;                на фазу) через новую LEP:GetPhaseCount. Округление
;                вверх - один раз, в самом конце - Claude)
;   1.7  (2026-07-22: ГЕОМЕТРИЧЕСКОЕ определение маршрута -
;                LEP:FindRoutesThroughPoints ищет, какие трассы реально
;                проходят через обе кликнутые опоры; при нескольких
;                кандидатах - один вопрос с запоминанием ответа на
;                сессию. Нужно для случая "маршрут 2 проложен поверх
;                опор маршрута 1" (общий участок двух фидеров) - опора
;                в XDATA помнит только тот маршрут, которым её
;                создали - Claude)
;   1.6  (2026-07-22: несколько проводов на одной паре
;                опор (общий участок двух маршрутов, или просто вторая
;                марка одного маршрута) больше НЕ рисуются друг на
;                друге - LEP:FindSamePolePairSpans находит уже
;                существующие пролёты на той же паре опор,
;                LEP:GetParallelOffset/OffsetPointList сдвигают новую
;                линию перпендикулярно, поочерёдно в разные стороны;
;                размерная линия рисуется только у первого пролёта на
;                паре опор (у остальных геометрия та же) - Claude)
;   1.5  (2026-07-22: Т-образное подключение веток -
;                проверка "опоры на одной трассе" из v1.4 переспрашивает,
;                а не отказывает намертво, если пользователь подтвердит
;                намеренное подключение опоры одной трассы к опоре
;                другой - геометрия пролёта в этом случае прямая линия
;                P1-P2 (нет единой трассы для нарезки по вершинам) -
;                Claude)
;   1.4  (2026-07-22: убран клик по маршруту в C:LEP-SPAN -
;                трасса определяется по ROUTE первой опоры
;                (LEP:FindRouteByID), со сверкой, что вторая опора той
;                же трассы; толщина линии пролёта по статусу
;                (LEP:SetEntityLWeight, как у опоры); новая команда
;                LEP-SPAN-REPAIR - чинит "осиротевшие" подписи после
;                ручного ERASE пролёта - Claude)
;   1.3  (2026-07-22: третий класс напряжения "6 кВ" -
;                выбор марки провода ВЛ переделан с бинарного if на
;                cond из трёх веток (10/6/0,4), иначе "6" молча попало
;                бы в ветку СИП-2 (0,4кВ) как "любой не 10" - Claude)
;   1.2  (2026-07-22, по просьбе пользователя: подпись
;                объединяется на весь однородный участок трассы вместо
;                одного пролёта - LEP:FinalizeSpanLabel/
;                GetSpanNeighbors/FindGroupMembers; подпись ВЛ теперь
;                БЕЗ запаса на провис (запас остаётся только в
;                ведомости), подпись КЛ - по-прежнему С запасом на
;                подъём кабеля (до дальнейших указаний); "+ подъём
;                кабеля по опоре" автоматически на обеих опорах КЛ-
;                пролёта; способ прокладки (ГНБ/Траншея) для Проект.
;                КЛ - Claude)
;   1.1  (LEP:CreateSpanLabel - "L=...м" на второй строке,
;                Claude, 2026-07-16)
;                1.0  (LEP:BringToFront для подписи пролёта и размерной
;                линии, Claude, 2026-07-15)
;                0.9  (КЛ больше не имеет своего типа линии - убран
;                LEP:EnsureLinetypeLoaded, КЛ рисуется CONTINUOUS как
;                ВЛ, Claude, 2026-07-15)
;                0.8  (комментарий LEP:CreateSpanDimension поправлен -
;                текст размера реально поворачивается вместе с линией
;                только теперь, DIMTIH/DIMTOH в LEP-SETUP.LSP -
;                Claude, 2026-07-15)
;                0.7  (LEP:CreateSpanLabel: фон под текстом выносок,
;                Claude, 2026-07-15)
;                0.6  (LEP:CreateSpanLabel: LEADER -> MLEADER, Claude, 2026-07-15)
;                0.5  (LEP:PickPole не принимает откосы/чужие блоки -
;                аудит Claude Fable, 2026-07-11)
;
;   ДОБАВЛЕНО В ЭТОЙ ВЕРСИИ:
;   Список марок ВЛ-провода теперь зависит от класса напряжения
;   МАРШРУТА (VCLASS в XDATA, см. LEP-ROUTE.LSP) - СИП-3
;   (*LEP-WireTypes-VL-10*) для 10кВ, СИП-2 (*LEP-WireTypes-VL-04*)
;   для 0,4кВ. Раньше был один общий список *LEP-WireTypes-VL* на все
;   случаи - физически СИП-2 и СИП-3 для разных классов напряжения не
;   взаимозаменяемы, старый список мог предложить не тот провод.
;
;   РАНЕЕ ДОБАВЛЕНО:
;   Расстояние между опорами (по прямой) и реальная длина провода/
;   кабеля, которую нужно закупить - теперь РАЗНЫЕ величины:
;     - LEP:GetRealLength - ВЛ получает запас на провис в процентах
;       (*LEP-Sag-VL*), КЛ - фиксированный запас на подъём на опору
;       (поконцово, LEP:GetEndReserve) ПЛЮС свой процент по прокладке
;       (*LEP-Sag-KL-GNB*/*LEP-Sag-KL-Trench*, добавлено 2026-07-24),
;       провод 10/6 кВ дополнительно умножается на число фаз
;       (LEP:GetPhaseCount) - все настройки в LEP-CONFIG.LSP. Результат
;       округляется единым правилом проекта (LEP:RoundLength) и идёт в
;       XDATA LENGTH, а значит в ведомость LEP-REPORT.
;     - LEP:CreateSpanDimensions (мн. ч.) - размерные линии (стрелками,
;       слой LEP-DIM) НА КАЖДЫЙ ПРЯМОЙ УЧАСТОК пролёта - это уже не про
;       материал, а про геометрию, для наглядности на чертеже.
;       ⚠️ 2026-08-05: и у КЛ, и у ВЛ (у ВЛ раньше была одна линия по
;       прямой на весь пролёт - см. шапку функции, почему включили).
;       Округляются ТОЙ ЖЕ LEP:RoundLength (⚠️ 2026-08-05, раньше тут
;       было своё, другое правило - и размер расходился с выноской
;       того же пролёта на метр).
;
;   ПЕРЕДЕЛАНО ПОЛНОСТЬЮ:
;   Старая версия выделяла ВСЮ полилинию маршрута целиком и красила
;   её в один слой через CHPROP - то есть у одной трассы мог быть
;   только один тип линии на всём протяжении, и именно на этом же
;   месте был краш ("bad argument type: stringp nil").
;
;   Новая логика: пролёт между ДВУМЯ ОПОРАМИ вырезается как
;   ОТДЕЛЬНЫЙ объект-полилиния (копия геометрии этого участка
;   маршрута), со своим слоем/типом линии под ВЛ или КЛ. Исходная
;   полилиния маршрута НЕ трогается и не удаляется - она остаётся
;   "невидимой арматурой", на ней по-прежнему держится привязка опор
;   (GEOMCONSTRAINT из LEP-POLE.LSP).
;
;   ОГРАНИЧЕНИЕ (честно, не прячу): новый объект-пролёт геометрически
;   скопирован с маршрута НА МОМЕНТ создания, но сам по себе не
;   связан через GEOMCONSTRAINT с опорами. Если потом подвинуть
;   опору - основная трасса подстроится, а нарисованный пролёт (с его
;   слоем/подписью) - нет, его нужно будет создать заново командой
;   LEP-SPAN. Это сознательное упрощение ради скорости - если это
;   неудобно, скажите, попробуем другой подход.
;
;   ВЫБОР ПРОЛЁТА: команда просит кликнуть по ДВУМ ТОЧКАМ - рядом с
;   первой опорой и рядом со второй опорой пролёта (а не "щёлкнуть по
;   линии"), потому что между двумя опорами в маршруте может быть
;   лишний изгиб без опоры - "клик по линии" в этом случае был бы
;   неоднозначным.
;
;   Марки проводов/кабелей вынесены в LEP-CONFIG.LSP
;   (*LEP-WireTypes-VL* / *LEP-WireTypes-KL*), как и просили - одно
;   место для расширения списка, а не хардкод в этом файле.
;
;   НАЗНАЧЕНИЕ:
;   Классификация пролётов маршрута (ВЛ/КЛ, марка провода/кабеля),
;   автоматический расчёт длины и подпись.
;
;=====================================================================
 
 
;; LEP:ChooseFromList перенесена в LEP-UTILS.LSP (используется и
;; здесь, и в LEP-POLE.LSP для списка типов опор - раньше была тут
;; в одном экземпляре, теперь общая).



;=====================================================================
; LEP:PickPole
;
; Клик ПО САМОМУ БЛОКУ ОПОРЫ (через entsel, не getpoint) - значит,
; работает обычная подсветка объекта при наведении курсора, как в
; любом другом выборе объектов AutoCAD. Возвращает ТОЧНУЮ точку
; вставки блока (без приближения по ближайшей точке).
;
; ⚠️ ФИКС 2026-07-11 (аудит): раньше проверялся только тип сущности
; (INSERT) - под проверку проходил ЛЮБОЙ блок, включая ОТКОС опоры
; (та же трапеция LEP-POLE-SYM, стоит в 2 м сбоку от трассы) и вообще
; посторонние блоки из подложки. Клик по откосу давал точку в 2 м от
; настоящей опоры - размерная линия и границы пролёта тихо считались
; от неверной точки. Теперь дополнительно проверяется XDATA: у
; ГЛАВНОЙ трапеции есть ключ TYPE=POLE (его пишет LEP:AddPoleData/
; LEP:AddEquipData), у откосов XDATA нет вообще (см.
; LEP:InsertPoleGroup - данные получает только главная) - это готовый
; естественный фильтр, отличающий настоящую опору от её откоса и от
; чужих блоков.
;
; Возвращает: (cons Точка Ent) или nil.
;
; ⚠️ ФИКС 2026-07-22: раньше возвращала ТОЛЬКО точку - для объединения
; подписей соседних пролётов (см. LEP:GetSpanNeighbors ниже) нужен
; ХЕНДЛ самой опоры, чтобы отличать "эти два пролёта касаются одной и
; той же опоры" НАДЁЖНО (по хендлу), а не по совпадению координат с
; допуском - на допуске уже ловили баги в этом проекте (см.
; *LEP-Vertex-Snap-Tolerance* в LEP-POLE.LSP). Оба места вызова в
; C:LEP-SPAN ниже поправлены под новый формат возврата (car/cdr).
;=====================================================================

(defun LEP:PickPole (PromptText / PickResult Ent EntData Pt Result)

    (setq PickResult (entsel PromptText))
    (setq Result nil)

    (if PickResult
        (progn
            (setq Ent (car PickResult))
            (setq EntData (entget Ent))

            ;; ✅ РАСШИРЕНО 2026-07-24: концом пролёта может быть не
            ;; только опора, но и наземный объект - КТП или кабельный
            ;; киоск (TYPE "KTP"/"KK"). Понадобилось для реального
            ;; случая: из КТП выходят два кабеля 0,4 кВ и идут в
            ;; кабельный киоск с двумя ПУ - опор на таком участке нет
            ;; ВООБЩЕ, и раньше такой пролёт было просто не нарисовать.
            ;;
            ;; Почему это оказалось так дёшево: КТП и киоск ставятся
            ;; ТЕМ ЖЕ способом, что и опора (LEP:InsertVertexOnRoute -
            ;; проекция клика на трассу + новая вершина + GEOMCONSTRAINT,
            ;; см. LEP-END.LSP), то есть с точки зрения пролёта это
            ;; такой же блок на вершине маршрута, со своим хендлом и
            ;; своим ROUTE в XDATA. Вся остальная механика (нарезка по
            ;; вершинам, объединение подписей, параллельный сдвиг,
            ;; размерная линия, трубы ГНБ) работает по хендлам и
            ;; вершинам и о типе объекта вообще не спрашивает.
            ;; ⚠️ 2026-07-24 (в тот же день): в список добавлен "TRANS" -
            ;; маркер смены способа прокладки (LEP-TRANSSYM.LSP). Он
            ;; вообще не оборудование, его единственная задача - быть
            ;; точкой, за которую цепляются концы ДВУХ пролётов с разным
            ;; способом прокладки (ГНБ до неё, траншея после). Способ
            ;; спрашивается один раз на пролёт, поэтому поделить
            ;; кабельный участок надвое можно только через объект.
            (if (and (= (cdr (assoc 0 EntData)) "INSERT")
                     (member (LEP:GetDataValue Ent "TYPE") '("POLE" "KTP" "KK" "TRANS"))
                )
                (progn
                    (setq Pt (cdr (assoc 10 EntData))) ; точка вставки блока - без приближений
                    (setq Result (cons Pt Ent))
                )
                (princ "\n[LEP-SPAN] Это не опора, не КТП, не киоск и не точка смены прокладки (возможно, откос или посторонний блок) - кликните по ГЛАВНОЙ трапеции опоры либо по символу КТП/киоска/маркера.")
            )
        )
    )

    Result
)
;=====================================================================
; LEP:GetNearestVertexIndex
;
; Находит индекс вершины в списке Verts, ближайшей к точке P.
;
; ⚠️ ФУНКЦИЯ ВОЗВРАЩАЕТ ИНДЕКС ВСЕГДА, КАКОЙ БЫ ДАЛЁКОЙ НИ БЫЛА
; "ближайшая" вершина - никакой проверки расстояния тут нет и быть не
; может (она не знает, зачем её спросили). Отсюда родилась целая
; тихая ошибка, см. LEP:EnsureVertexAtPoint ниже - проверять
; расстояние обязана ВЫЗЫВАЮЩАЯ сторона.
;=====================================================================
 
(defun LEP:GetNearestVertexIndex (Verts P / i V Dist BestIdx BestDist)
 
    (setq i 0)
    (setq BestDist nil)
    (setq BestIdx 0)
 
    (foreach V Verts
        (setq Dist (distance P V))
        (if (or (not BestDist) (< Dist BestDist))
            (progn
                (setq BestDist Dist)
                (setq BestIdx i)
            )
        )
        (setq i (1+ i))
    )
 
    BestIdx
)


;=====================================================================
; LEP:EnsureVertexAtPoint     (НОВАЯ 2026-08-05)
;
; Проверяет, что у маршрута Route ЕСТЬ ВЕРШИНА в точке Pt (там, где
; стоит кликнутая опора), и если её нет - вставляет. Возвращает T,
; если после работы функции пролёт можно строить, и nil, если строить
; нельзя (опора вообще не на этом маршруте).
;
; ЗАЧЕМ - НАЙДЕННАЯ ТИХАЯ ОШИБКА (2026-08-05). Разбирали сценарий
; пользователя: "в маршрут 1 вливается маршрут 2, идущий из другого
; места к той же ТП". На общем участке провода обоих фидеров висят на
; ОДНИХ И ТЕХ ЖЕ опорах - но опоры эти принадлежат маршруту 1, и
; вершины при их установке вставлялись В ПОЛИЛИНИЮ МАРШРУТА 1
; (LEP:InsertVertexOnRoute, LEP-POLE.LSP). Когда пользователь потом
; рисует маршрут 2 поверх, у ЕГО полилинии вершины стоят там, где он
; кликал мышкой при рисовании - на опорах маршрута 1 их нет вообще.
;
; Дальше две функции работают с РАЗНОЙ строгостью, и в этом зазоре
; всё и происходит:
;   - LEP:FindRoutesThroughPoints честно находит маршрут 2, потому что
;     меряет расстояние ДО ЛИНИИ (с допуском *LEP-Route-Detect-
;     Tolerance*, 1 м) - и она действительно проходит рядом с опорой;
;   - а LEP:GetNearestVertexIndex привязывается К БЛИЖАЙШЕЙ ВЕРШИНЕ, и
;     НИКАКОГО допуска у неё нет. Она молча вернёт вершину, до которой
;     хоть пятьдесят метров.
;
; Итог до этой правки: пролёт строился от вершины, которая может быть
; далеко от кликнутой опоры. Длина неверная, а на чертеже линия просто
; чуть-чуть не достаёт до опоры или проскакивает мимо - и это очень
; легко не заметить.
;
; ⚠️ ОСОБЕННО КОВАРНО В ПАРЕ С МАССОВЫМ КЛИКОМ (правка того же дня,
; "кликни первую и последнюю опору"). Кликая СОСЕДНИЕ опоры, ты с
; большой вероятностью попадал двумя кликами в ОДНУ И ТУ ЖЕ вершину
; маршрута 2, индексы совпадали, и команда честно говорила "между
; этими точками нет отдельного участка маршрута" - ошибку было ВИДНО.
; А при клике "первая -> последняя" индексы почти наверняка разные, и
; ошибка становится полностью бесшумной. То есть удобная правка
; попутно спрятала бы существующий баг - поэтому чиним здесь и сейчас.
;
; ЧТО ДЕЛАЕТ (три случая, по возрастанию тяжести):
;   1. Вершина в этой точке есть (ближе *LEP-Span-VertexGap-Tolerance*)
;      - обычный случай, НИЧЕГО не делаем, возвращаем T. Это 99%
;      вызовов: символ опоры стоит РОВНО в вершине своего маршрута
;      (LEP:PlacePoleOnRoute), расстояние там нулевое.
;   2. Вершины нет, но САМА ЛИНИЯ маршрута проходит рядом с опорой
;      (ближе *LEP-Route-Detect-Tolerance*) - это и есть случай "чужая
;      опора на общем участке". Вставляем вершину (той же
;      LEP:InsertVertexOnRoute, что и при постановке опоры), громко
;      пишем об этом в консоль, возвращаем T. Маршрут от этого не
;      деформируется: вершина ложится НА линию, в точку проекции.
;      Побочная польза - следующий пролёт на этой опоре сработает уже
;      без вставки.
;   3. Опора далеко и от вершин, и от самой линии - значит она вообще
;      не на этом маршруте. Тут догадываться нельзя: любая вставка
;      деформировала бы трассу. Громко ругаемся и возвращаем nil,
;      пролёт не строится.
;
; ⚠️ Т-образное подключение (IsCrossRoute) сюда НЕ ПОПАДАЕТ - там
; вершины подставляются искусственно, прямо из кликнутых точек, и
; проверять нечего. См. место вызова в C:LEP-SPAN.
;
; ⚠️ Функция МЕНЯЕТ полилинию маршрута (случай 2), поэтому вызывающая
; сторона обязана перечитать вершины (LEP:GetVertices) ПОСЛЕ вызова, а
; не до - иначе будет работать со старым списком без новой вершины.
;=====================================================================

(defun LEP:EnsureVertexAtPoint (Route Pt / Verts Idx VertGap LinePt LineGap)

    (setq Verts (LEP:GetVertices Route))

    ;; Полилиния короче 2 вершин - вырожденная, LEP:FindNearestSegment
    ;; на ней не работает. Не падаем, просто отказываемся.
    (if (< (length Verts) 2)
        (progn
            (princ "\n[LEP-SPAN] ⚠️ У выбранного маршрута меньше двух вершин - пролёт не построить.")
            nil
        )
        (progn
            (setq Idx (LEP:GetNearestVertexIndex Verts Pt))
            (setq VertGap (distance Pt (nth Idx Verts)))

            (cond

                ;; Случай 1 - вершина на месте, обычная работа.
                ((<= VertGap *LEP-Span-VertexGap-Tolerance*)
                    T
                )

                ;; Случай 2 - вершины нет, но линия рядом: чужая опора
                ;; на общем участке двух маршрутов. Вставляем вершину.
                (t
                    (setq LinePt (cadr (LEP:FindNearestSegment Verts Pt)))
                    (setq LineGap (distance Pt LinePt))

                    (if (<= LineGap *LEP-Route-Detect-Tolerance*)
                        (progn
                            (LEP:InsertVertexOnRoute Route Pt)
                            (princ
                                (strcat
                                    "\n[LEP-SPAN] У этой опоры не было вершины на выбранном маршруте (ближайшая была в "
                                    (rtos VertGap 2 1)
                                    " м) - вершина добавлена. Так бывает на общем участке двух маршрутов."
                                )
                            )
                            T
                        )
                        (progn
                            (princ
                                (strcat
                                    "\n[LEP-SPAN] ⚠️ ОТМЕНА: кликнутый объект НЕ на выбранном маршруте - до его линии "
                                    (rtos LineGap 2 1)
                                    " м, до ближайшей вершины "
                                    (rtos VertGap 2 1)
                                    " м. Пролёт НЕ построен - иначе он молча уехал бы концом не туда."
                                )
                            )
                            (princ "\n[LEP-SPAN] Что делать: проверьте, те ли объекты кликнули, либо подтвердите Т-образное подключение при вопросе о разных трассах.")
                            nil
                        )
                    )
                )
            )
        )
    )
)


;=====================================================================
; LEP:SubList
;
; Возвращает подсписок List от индекса From до индекса To включительно.
;=====================================================================
 
(defun LEP:SubList (Lst From To / Result i Item)
    (setq Result nil)
    (setq i 0)
    (foreach Item Lst
        (if (and (>= i From) (<= i To))
            (setq Result (append Result (list Item)))
        )
        (setq i (1+ i))
    )
    Result
)
 
 
;=====================================================================
; LEP:CreateSpanEntity
;
; Создаёт отдельный объект-полилинию для пролёта (список точек
; SubVerts), на нужном слое/типе линии. Возвращает ename нового
; объекта.
;=====================================================================
 
(defun LEP:CreateSpanEntity (SubVerts LayerName LtName / EntList V)
 
    (setq EntList
        (list
            '(0 . "LWPOLYLINE")
            '(100 . "AcDbEntity")
            (cons 8 LayerName)
            (cons 6 LtName)
            '(100 . "AcDbPolyline")
            (cons 90 (length SubVerts))
            '(70 . 0)
        )
    )
 
    (foreach V SubVerts
        (setq EntList (append EntList (list (cons 10 V))))
    )
 
    (entmake EntList)
    (entlast)
)
 
 
;=====================================================================
; LEP:GetSpanLength
;
; Суммарная длина пролёта - сумма расстояний между соседними точками
; списка SubVerts (для прямых участков без дуг). Это геометрический
; путь ВДОЛЬ трассы - используется как основа для расчёта реальной
; длины материала (LEP:GetRealLength), НЕ то же самое, что прямое
; расстояние между самими опорами (см. LEP:CreateSpanDimension).
;=====================================================================

(defun LEP:GetSpanLength (SubVerts / i Total)

    (setq Total 0.0)
    (setq i 0)

    (while (< i (1- (length SubVerts)))
        (setq Total (+ Total (distance (nth i SubVerts) (nth (1+ i) SubVerts))))
        (setq i (1+ i))
    )

    Total
)


;=====================================================================
; LEP:GetPhaseCount
;
; Сколько ОТДЕЛЬНЫХ проводов надо на один пролёт - множитель к длине
; материала.
;
; ✅ ДОБАВЛЕНО 2026-07-24 (новое правило от пользователя): у высокого
; напряжения (10 кВ и 6 кВ) провод СИП-3 - на КАЖДУЮ фазу идёт свой
; отдельный провод, значит на один пролёт нужно ТРИ длины, а не одна.
; У 0,4 кВ провод СИП-2 - там все жилы уже собраны в один жгут, длина
; считается один раз (множитель 1).
;
; ⚠️ К КАБЕЛЮ (KL) множитель НЕ применяется НИКОГДА, даже на 10 кВ:
; кабель 10 кВ трёхжильный, это одна строительная длина, а не три.
; Именно поэтому функция принимает TypeCode, а не только класс.
;
; Множители лежат в *LEP-Phases-ByClass* (LEP-CONFIG.LSP). Если класс
; напряжения по какой-то причине не найден в списке (старый пролёт без
; VCLASS у маршрута, опечатка в коде класса) - возвращаем 1, то есть
; считаем в одну нитку. Это СОЗНАТЕЛЬНО осторожный вариант: лучше
; недосчитать и увидеть заниженное число в ведомости, чем молча
; утроить длину там, где утраивать не надо.
;=====================================================================

(defun LEP:GetPhaseCount (TypeCode VClass / Found)

    (if (= TypeCode "VL")
        (progn
            (setq Found (assoc VClass *LEP-Phases-ByClass*))
            (if Found (cdr Found) 1)
        )
        1
    )
)


;=====================================================================
; LEP:GetRealLength
;
; Реальная длина провода/кабеля с запасом - ОТДЕЛЬНАЯ величина от
; расстояния между опорами. Все настройки - в LEP-CONFIG.LSP, раздел
; "ЗАПАС ДЛИНЫ ПРОВОДА/КАБЕЛЯ".
;
; ✅ ПЕРЕПИСАНО 2026-07-24 под новые нормы запаса от пользователя.
; Общая формула теперь ОДНА для обоих типов:
;
;     ( база + фикс.добавка ) x ( 1 + процент/100 ) x число_фаз
;
; и различаются только слагаемые:
;
;   ВЛ (провод):
;     - фикс. добавки нет;
;     - процент - *LEP-Sag-VL* (4,5%), запас на провис между опорами;
;     - число фаз - 3 для 10/6 кВ, 1 для 0,4 кВ (LEP:GetPhaseCount
;       выше). Умножение идёт ПОСЛЕ процента - прямая формулировка
;       пользователя ("умножаем на 3 после прибавления запасиков").
;
;   КЛ (кабель):
;     - фикс. добавка Reserve - метры на КОНЦЕВЫЕ ЗАДЕЛКИ, считаются
;       ПОКОНЦОВО вызывающей стороной (LEP:GetEndReserve ниже) и
;       передаются сюда готовым числом. Это РЕАЛЬНАЯ физическая длина
;       кабеля, а не запас на закупку (уточнено пользователем
;       2026-07-22): у опоры кабель лезет наверх (3 м), у наземной
;       КТП/киоска - никуда не лезет (сейчас 0 м);
;     - процент СВОЙ для каждого способа прокладки: ГНБ (в трубе) -
;       *LEP-Sag-KL-GNB* (2%), траншея - *LEP-Sag-KL-Trench* (4%).
;       В трубе кабель протягивают почти прямо, поэтому запас меньше;
;       в траншее его укладывают "змейкой" по неровному дну - больше;
;     - число фаз всегда 1 (см. LEP:GetPhaseCount).
;
;   ⚠️ Проценты КЛ идут ПОВЕРХ метров концевых заделок, а не вместо
;   них (решение пользователя 2026-07-24) - это разные величины, см.
;   подробное обоснование в LEP-CONFIG.LSP.
;
; Округление - ЕДИНЫМ правилом проекта (LEP:RoundLength, LEP-UTILS.LSP):
; выше *LEP-Round-UpThreshold* вверх, ниже - по правилам математики.
; ⚠️ ИЗМЕНЕНО 2026-08-05: здесь стоял безусловный LEP:RoundUp. Правило
; "для закупки округляем только вверх" было верным по сути, но жило
; тут В ОДИНОЧКУ - а размерная линия рядом округляла по математике, и
; на живом чертеже один и тот же пролёт 46,4958 м получил "L=47 м" в
; выноске и "46 м" в размере. Соблазн оставить ведомости отдельное
; правило был, но тогда бы разъехались выноска и строка CSV - то же
; расхождение, только в другом месте. Цена нового правила: пролёт
; короче порога может уйти вниз, максимум на 0,5 м; практически это
; почти не случается, потому что проценты запаса (см. ниже) сами
; перекидывают число через целое.
; ⚠️ Округляем ОДИН раз, в самом конце, уже ПОСЛЕ умножения на число
; фаз - а не отдельно каждую фазу. Иначе на трёхфазной линии мы бы
; трижды докидывали "хвостик" округления и завышали ведомость.
;
; Запас на муфты/разделку кабеля СОЗНАТЕЛЬНО не считается - остаётся
; на усмотрение проектировщика при подготовке настоящей сметы, эта
; программа даёт только черновую прикидку.
;
; Аргументы:
;   TypeCode   - "VL" или "KL" (cdr от LineType - см. C:LEP-SPAN);
;   Method     - "GNB"/"TRENCH" для проектируемой КЛ, иначе nil
;                (у ВЛ не используется вообще; у СУЩЕСТВУЮЩЕЙ КЛ
;                способ прокладки не спрашивается - там nil, и тогда
;                берётся процент траншеи как более осторожный из двух.
;                На ведомость это не влияет: она считает только
;                Проект., см. LEP-REPORT.LSP - число нужно лишь для
;                подписи на чертеже);
;   VClass     - класс напряжения маршрута ("10"/"6"/"04", XDATA
;                маршрута, см. LEP-ROUTE.LSP);
;   SpanLength - сырая длина пролёта вдоль трассы, м;
;   Reserve    - метры на концевые заделки, уже посчитанные поконцово
;                (LEP:GetEndReserve ниже). У ВЛ игнорируется.
;=====================================================================

(defun LEP:GetRealLength (TypeCode Method VClass SpanLength Reserve / Base Pct)

    (if (= TypeCode "VL")
        (progn
            (setq Base SpanLength)
            (setq Pct  *LEP-Sag-VL*)
        )
        (progn
            (setq Base (+ SpanLength Reserve))
            (setq Pct
                (if (= Method "GNB")
                    *LEP-Sag-KL-GNB*
                    *LEP-Sag-KL-Trench*
                )
            )
        )
    )

    (LEP:RoundLength
        (* Base
           (+ 1.0 (/ Pct 100.0))
           (LEP:GetPhaseCount TypeCode VClass)
        )
    )
)


;=====================================================================
; LEP:GetDisplayLength
;
; Длина, которая пишется В ПОДПИСИ НА ЧЕРТЕЖЕ - НАМЕРЕННО другая
; величина, чем длина для ведомости (LEP:GetRealLength выше).
;
; ✅ ДОБАВЛЕНО 2026-07-24 по прямому указанию пользователя: "кабель и
; провод на чертеже показываешь без запаса (только подъём +6
; остаётся), все запасы идут только в ведомость".
;
; То есть на чертеже - ТОЛЬКО ФИЗИКА, ничего "на закупку":
;   ВЛ - сырая длина как есть. Провис провисом, но на плане провод
;        нарисован по трассе, и подпись должна совпадать с тем, что
;        человек видит и может померить линейкой.
;   КЛ - сырая длина ПЛЮС метры концевых заделок. Они остаются,
;        потому что это НЕ запас, а реальный кусок кабеля: у опоры он
;        физически лезет наверх. У наземных концов (КТП/киоск) этих
;        метров сейчас ноль - лезть некуда, см. *LEP-KL-Reserve-Pole*/
;        *LEP-KL-Reserve-Ground* в LEP-CONFIG.LSP.
;
; Всё остальное (процент на провис/укладку, множитель фаз у 10/6 кВ)
; на чертеж НЕ попадает вообще - оно живёт только в XDATA LENGTH и в
; CSV-ведомости.
;
; ⚠️ Функция НЕ округляет - округление делает вызывающая сторона, ОДИН
; раз на всю группу пролётов. Округлять здесь означало бы округлять
; каждый пролёт по отдельности и копить лишние "хвостики".
;
; ⚠️ ИЗМЕНЕНО 2026-07-24 (в тот же день, что и добавлено): третий
; аргумент был "сколько пролётов в группе" и метры домножались на него.
; Это работало, пока запас был одинаковым у всех пролётов (жёсткие 6 м).
; После перехода на поконцовый расчёт у РАЗНЫХ пролётов одной группы
; запас может быть разным (пролёт КТП-опора = 3 м, следующий
; опора-опора = 6 м), и "число пролётов x константа" стало
; неправильным. Теперь сюда передаётся УЖЕ ГОТОВАЯ СУММА запасов всех
; пролётов группы - она складывается из ключа RESERVE в XDATA каждого
; пролёта (см. LEP:FinalizeSpanLabel).
;
; Аргументы:
;   TypeCode     - "VL" или "KL";
;   RawLength    - суммарная СЫРАЯ длина группы (сумма RAWLENGTH), м;
;   ReserveTotal - суммарные метры концевых заделок всех пролётов
;                  группы (сумма RESERVE); у ВЛ не используется.
;=====================================================================

(defun LEP:GetDisplayLength (TypeCode RawLength ReserveTotal)

    (if (= TypeCode "VL")
        RawLength
        (+ RawLength ReserveTotal)
    )
)


;=====================================================================
; LEP:GetEndReserve
;
; Метры кабеля на КОНЦЕВЫЕ ЗАДЕЛКИ пролёта - считаются ПОКОНЦОВО, по
; типу того, что на конце реально стоит.
;
; ✅ ДОБАВЛЕНО 2026-07-24. Раньше на пролёт шла одна жёсткая константа
; *LEP-KL-Reserve* = 6 м ("по 3 м с каждой стороны на подъём кабеля на
; опору") - и это было верно, пока ОБА конца пролёта всегда были
; опорами. Появился реальный случай, где не опора НИ ОДИН конец: из
; КТП выходят два кабеля 0,4 кВ и заходят в кабельный киоск. Из
; наземной подстанции кабель выходит внизу и в киоск заходит внизу -
; лезть ему некуда, и жёсткие 6 м были бы чистым завышением на каждом
; таком пролёте.
;
; Теперь: опора -> *LEP-KL-Reserve-Pole* (3 м), КТП/киоск ->
; *LEP-KL-Reserve-Ground* (сейчас 0 м, константа заведена на будущее -
; см. подробное обоснование в LEP-CONFIG.LSP). Отсюда опора-опора = 6 м
; (ровно как было, ничего не изменилось), КТП-опора = 3 м,
; КТП-киоск = 0 м.
;
; ⚠️ Неизвестный/отсутствующий TYPE трактуется как ОПОРА, а не как ноль.
; Так безопаснее: единственный способ сюда попасть - объект, созданный
; старой версией программы или руками, а до сегодняшнего дня концом
; пролёта могла быть ТОЛЬКО опора. То есть при сомнении мы
; воспроизводим прежнее поведение, а не молча обнуляем запас.
;
; Аргументы: Ent1/Ent2 - ename объектов на концах пролёта.
;
; Разбита на две функции (одна считает ОДИН конец, вторая складывает
; два) СОЗНАТЕЛЬНО - вместо локальной lambda внутри одной функции:
; вызов лямбды, лежащей в локальной переменной, в AutoLISP работает не
; так очевидно, как в обычном Lisp, а проверить это вживую в консоли
; сейчас негде. Две обычные defun-функции ведут себя предсказуемо и
; читаются не хуже.
;=====================================================================

(defun LEP:GetOneEndReserve (Ent / EntType)

    (setq EntType (LEP:GetDataValue Ent "TYPE"))

    ;; ⚠️ "TRANS" (маркер смены способа прокладки) добавлен сюда ЯВНО
    ;; 2026-07-24. Список перечисляет то, у чего запаса НЕТ, а всё
    ;; остальное считается опорой - значит забудь тут маркер, и он
    ;; молча получил бы 3 м "на подъём по опоре", хотя кабель в этой
    ;; точке вообще не заканчивается: он идёт дальше сплошным куском,
    ;; просто меняется способ прокладки. Причём ошибка была бы двойной:
    ;; лишние 3 м у конца первого пролёта И ещё 3 м у начала второго.
    (if (member EntType '("KTP" "KK" "TRANS"))
        *LEP-KL-Reserve-Ground*
        *LEP-KL-Reserve-Pole*
    )
)


(defun LEP:GetEndReserve (Ent1 Ent2)
    (+ (LEP:GetOneEndReserve Ent1) (LEP:GetOneEndReserve Ent2))
)


;=====================================================================
; LEP:CreateSpanDimension
;
; Линейный размер (стрелками, LEP-DIM слой) между двумя точками -
; ПРЯМОЕ расстояние P1-P2 (не путь вдоль трассы, а "по линейке", как
; в классическом черчении). Это ОТДЕЛЬНАЯ величина от реальной длины
; провода/кабеля с запасом (LEP:GetRealLength) - показывает геометрию,
; а не сколько материала нужно закупить.
;
; ⚠️ 2026-08-05: НАПРЯМУЮ ИЗ C:LEP-SPAN БОЛЬШЕ НЕ ВЫЗЫВАЕТСЯ. Теперь
; это "кирпич", который в цикле дёргает LEP:CreateSpanDimensions
; (мн. ч.) - по одному размеру на каждый прямой участок пролёта, и у
; КЛ, и у ВЛ. Соответственно P1/P2 здесь - две СОСЕДНИЕ ВЕРШИНЫ, а не
; обязательно две опоры (у пролёта между соседними опорами это одно и
; то же). Функцию НЕ удалять и не встраивать в вызывающую - вся
; возня с перпендикулярным сдвигом и переопределением текста живёт
; здесь и нужна на каждый участок.
;
; Размерная линия сдвинута от прямой P1-P2 ПЕРПЕНДИКУЛЯРНО на
; *LEP-LeaderOffset*, чтобы не накладываться на сам нарисованный
; пролёт (перпендикуляр к направлению P1->P2, а не диагональный
; сдвиг, как у текстовых подписей - для размерной линии так привычнее
; и аккуратнее смотрится).
;
; Текст размера ПЕРЕОПРЕДЕЛЁН вручную через опцию "_Text" у DIMALIGNED
; на заранее округлённое DimDistance (целое число метров, единое
; правило округления - LEP:RoundLength, считается в
; LEP:CreateSpanDimensions) - без
; этого DIMALIGNED сам измерил бы точное расстояние с дробной частью,
; а нам нужно именно круглое число.
;
; DIMALIGNED вместо DIMLINEAR (замена от 2026-07-10, по просьбе
; пользователя): DIMLINEAR всегда рисует размер строго горизонтально
; или вертикально, а пролёт между опорами может идти под любым углом -
; из-за этого размерная линия визуально "отрывалась" от самого пролёта.
; DIMALIGNED рисует размерную линию ПАРАЛЛЕЛЬНО отрезку P1-P2, что для
; пролёта ЛЭП геометрически правильнее. Порядок аргументов у command
; для DIMALIGNED с опцией "_Text" повторяет DIMLINEAR - обе команды
; из одного семейства "линейных" размеров AutoCAD с одинаковой
; последовательностью запросов (первая точка выноски, вторая точка
; выноски, положение размерной линии/[Mtext/Text/Angle]), поэтому
; порядок аргументов ниже не менялся.
;
; ⚠️ ФИКС 2026-07-15 (жалоба пользователя): старая версия этого
; комментария утверждала "текст поворачивается вместе с линией" - это
; НЕ было проверено вживую и оказалось НЕВЕРНО: DIMTIH/DIMTOH никогда
; явно не выставлялись, поэтому держался дефолт AutoCAD (=1, текст
; ВСЕГДА горизонтален). Теперь `C:LEP-SETUP` (LEP-SETUP.LSP)
; выставляет DIMTIH=DIMTOH=0 (текст поворачивается вместе с линией) и
; DIMTAD=1 (текст НАД линией, не разрывает её) - см. подробности в
; LEP-CONFIG.LSP, раздел "ОРИЕНТАЦИЯ ТЕКСТА РАЗМЕРНОЙ ЛИНИИ ПРОЛЁТА".
;=====================================================================

(defun LEP:CreateSpanDimension (P1 P2 DimDistance / OldLayer Dx Dy Len Nx Ny MidX MidY DimLocPt DimText)

    (setq OldLayer (getvar "CLAYER"))
    (LEP:SetCurrentLayer *LEP-Layer-Dim*)

    (setq Dx (- (car P2) (car P1)))
    (setq Dy (- (cadr P2) (cadr P1)))
    (setq Len (distance P1 P2))

    (if (> Len 1e-9)
        (progn
            ;; Единичный перпендикуляр к направлению P1->P2 - в какую
            ;; сторону сдвинуть размерную линию от самого пролёта.
            (setq Nx (/ (- Dy) Len))
            (setq Ny (/ Dx Len))

            (setq MidX (/ (+ (car P1) (car P2)) 2.0))
            (setq MidY (/ (+ (cadr P1) (cadr P2)) 2.0))

            (setq DimLocPt
                (list
                    (+ MidX (* Nx *LEP-LeaderOffset*))
                    (+ MidY (* Ny *LEP-LeaderOffset*))
                )
            )

            (setq DimText (strcat (itoa DimDistance) " м"))

            (command "_.DIMALIGNED" P1 P2 "_Text" DimText DimLocPt)

            ;; Порядок отрисовки - наверх (по просьбе пользователя
            ;; 2026-07-15, см. LEP:BringToFront, LEP-UTILS.LSP).
            (LEP:BringToFront (entlast))
        )
    )

    (setvar "CLAYER" OldLayer)
)


;=====================================================================
; LEP:CollectNodePoints     (НОВАЯ 2026-08-20)
;
; Точки вставки ВСЕХ "узловых" блоков чертежа - опор, МТП, РЛК, КТП,
; кабельных киосков и маркеров смены способа прокладки. Нужна для
; LEP:CollapseDimVertices ниже: из двух почти совпавших вершин
; маршрута представителем должна стать та, где реально что-то стоит.
;
; Собирается ОДИН РАЗ на вызов (как и список существующих размеров в
; LEP:CreateSpanDimensions) - на чертеже с сотней опор и десятком
; участков поштучное сканирование дало бы тысячу лишних чтений.
;
; ⚠️ В набор попадают И ОТКОСЫ 2-/3-стоечных опор: это блоки на том же
; слое, просто без XDATA. Отдельно фильтровать их не нужно - они стоят
; в *LEP-Pole-Sym-Offset* (2 м) от вершины, то есть заведомо дальше
; *LEP-Dim-NodeSnap* (0,3 м), и на выбор представителя не влияют.
; Именно поэтому NodeSnap нельзя задирать до метра-двух.
;=====================================================================

(defun LEP:CollectNodePoints (/ SS i Result)

    (setq Result nil)

    (setq SS
        (ssget "_X"
            (list
                '(0 . "INSERT")
                (cons 8
                    (strcat
                        *LEP-Layer-Proj-Pole* "," *LEP-Layer-Exist-Pole* ","
                        *LEP-Layer-Proj-MTP* "," *LEP-Layer-Proj-RLK* ","
                        *LEP-Layer-Proj-TP* "," *LEP-Layer-Exist-TP* ","
                        *LEP-Layer-Transition*
                    )
                )
            )
        )
    )

    (if SS
        (progn
            (setq i 0)
            (repeat (sslength SS)
                (setq Result (cons (cdr (assoc 10 (entget (ssname SS i)))) Result))
                (setq i (1+ i))
            )
        )
    )

    Result
)


;=====================================================================
; LEP:VertexHasNode     (НОВАЯ 2026-08-20)
;
; Стоит ли в точке Pt какой-нибудь узловой блок (список Nodes от
; LEP:CollectNodePoints)? Допуск - *LEP-Dim-NodeSnap*.
;
; ⚠️ Вершины полилинии ДВУМЕРНЫЕ (см. LEP:GetVertices), а точка
; вставки блока - трёхмерная. Это нормально: если хотя бы один
; аргумент distance двумерный, Z игнорируется у обоих.
;=====================================================================

(defun LEP:VertexHasNode (Pt Nodes / Found)

    (setq Found nil)

    (foreach N Nodes
        (if (and (not Found) (<= (distance Pt N) *LEP-Dim-NodeSnap*))
            (setq Found T)
        )
    )

    Found
)


;=====================================================================
; LEP:CollapseDimVertices     (НОВАЯ 2026-08-20)
;
; Схлопывает близко стоящие вершины маршрута в ОДИН узел - чтобы
; размеры шли от опоры до опоры, а не от опоры до случайной вершины
; в полуметре от неё.
;
; ЗАЧЕМ (случай пользователя 2026-08-20, разобран по живому чертежу).
; Размеры ставятся на КАЖДЫЙ участок между соседними вершинами
; (см. LEP:CreateSpanDimensions ниже) - и это правильно для траншеи
; "молнией". Но угловая опора почти всегда встаёт рядом с изломом,
; который пользователь нарисовал руками, а снап
; *LEP-Vertex-Snap-Tolerance* всего 10 см - клик мимо, и
; LEP:InsertVertexOnRoute вставляет ВТОРУЮ вершину в 20-80 см от
; первой. На чертеже пользователя из 26 вершин пять оказались такими
; парами: 29,25 + 0,75 = 30,00 - шаг опор целый, а размера два,
; "29 м" и "1 м". Второй на чертеже выглядит как ошибка, потому что
; ошибка и есть.
;
; КАК РАБОТАЕТ. Идём по вершинам слева направо и режем список на
; КЛАСТЕРЫ: все вершины в пределах *LEP-Dim-NodeGap* (2 м) от начала
; кластера считаются одним узлом. От каждого кластера в итоговый
; список идёт ОДИН представитель:
;   - у ПЕРВОГО кластера - первая вершина, у ПОСЛЕДНЕГО - последняя.
;     Это концы пролёта (кликнутые опоры), размер обязан доставать
;     ровно до них;
;   - у остальных - первая вершина, где РЕАЛЬНО стоит блок
;     (LEP:VertexHasNode), а если блока нет ни в одной - просто
;     первая. Без этого правила представителем стал бы нарисованный
;     руками излом, и размер начинался бы в 0,75 м от опоры: на
;     печати это видно.
;
; ⚠️ ПОЧЕМУ НЕ "ПРОПУСКАТЬ КОРОТКИЕ УЧАСТКИ". Тогда 0,75 м просто
; исчезли бы из чертежа, и сумма размеров перестала бы сходиться с
; трассой (29 вместо 30). Схлопывание сохраняет длину: узел один,
; расстояние меряется до следующего узла целиком.
;
; ⚠️ ПОЧЕМУ НЕ ПО УГЛУ ИЗЛОМА. Опоры на прямом участке ВЛ стоят РОВНО
; коллинеарно - фильтр "выкинуть всё, что на прямой" убил бы все
; размеры между ними, то есть ровно то, ради чего посегментные
; размеры включали для ВЛ 2026-08-05. Вдобавок на живом чертеже
; паразитные вершины давали излом 0,0°, а СОСЕДНИЕ с ними настоящие
; изломы трассы - 3-4°: по углу их не разделить в принципе.
;
; ⚠️ ЭТО ТОЛЬКО ПРО РАЗМЕРЫ. Длина пролёта, XDATA и сам провод
; считаются по ПОЛНОМУ списку вершин - там лишняя вершина ничего не
; портит (сумма отрезков та же). Схлопнутый список нигде, кроме
; простановки размеров, не используется.
;
; Вырожденные случаи: меньше трёх вершин - возвращаем как есть, там
; схлопывать нечего. Если схлопнулось до одной точки (весь пролёт
; короче NodeGap) - тоже возвращаем исходный список: лучше странный
; размер, чем ни одного.
;=====================================================================

(defun LEP:CollapseDimVertices (Verts / Nodes N i j Start Cluster RepIdx K Result)

    (setq N (length Verts))

    (if (< N 3)
        Verts
        (progn

            (setq Nodes (LEP:CollectNodePoints))
            (setq Result nil)
            (setq i 0)

            (while (< i N)

                (setq Start (nth i Verts))
                (setq j (1+ i))
                (setq Cluster (list i))

                ;; Расстояние меряется от НАЧАЛА кластера, а не от
                ;; предыдущей вершины: иначе цепочка вершин с шагом
                ;; 1,9 м схлопнулась бы целиком, каким бы длинным ни
                ;; был участок.
                (while (and (< j N)
                            (< (distance Start (nth j Verts)) *LEP-Dim-NodeGap*)
                       )
                    (setq Cluster (append Cluster (list j)))
                    (setq j (1+ j))
                )

                (cond

                    ;; Начало пролёта - кликнутая опора, берём как есть.
                    ((= i 0) (setq RepIdx 0))

                    ;; Кластер дотянулся до конца списка - значит в нём
                    ;; сидит вторая кликнутая опора, и представителем
                    ;; должна быть именно она.
                    ((>= j N) (setq RepIdx (1- N)))

                    ;; Середина: первая вершина с блоком, иначе первая.
                    (t
                        (setq RepIdx nil)
                        (foreach K Cluster
                            (if (and (not RepIdx)
                                     (LEP:VertexHasNode (nth K Verts) Nodes)
                                )
                                (setq RepIdx K)
                            )
                        )
                        (if (not RepIdx) (setq RepIdx (car Cluster)))
                    )
                )

                (setq Result (append Result (list (nth RepIdx Verts))))
                (setq i j)
            )

            (if (< (length Result) 2) Verts Result)
        )
    )
)


;=====================================================================
; LEP:CreateSpanDimensions   (⚠️ МНОЖЕСТВЕННОЕ ЧИСЛО, НОВАЯ 2026-08-04)
;
; Рисует размерную линию НА КАЖДЫЙ ПРЯМОЙ УЧАСТОК пролёта - по одной
; между каждой парой соседних вершин списка Verts, вместо ОДНОЙ линии
; "по прямой от конца до конца".
;
; ЗАЧЕМ (случай пользователя 2026-08-04). Кабельная траншея часто идёт
; "молнией" - несколько колен между двумя объектами. Одна размерная
; линия от начала до конца показывала бы ПРЯМОЕ расстояние между
; концами: число меньше того, что реально копают, и по нему нельзя
; посчитать объём земляных работ. Дословно: "при таком виде траншеи
; надо показывать каждый участок до вершины, чтобы понимать сколько
; копать и объёмы".
;
; ⚠️ ЭТО ЛЕЧИТ ПРИЧИНУ, А НЕ СИМПТОМ. До этой правки, чтобы получить
; размер на каждое колено, приходилось ставить на каждом повороте
; маркер точки разрыва - только ради того, чтобы колено стало
; отдельным пролётом. Побочный эффект был неприятный: маркеры рвали и
; ПОДПИСЬ тоже (см. LEP:GetSpanNeighbors), и одна траншея выглядела
; как несколько разных. Теперь размеры по коленам получаются сами, и
; **ставить маркеры на поворотах больше не нужно**.
;
; ✅ 2026-08-05: ТЕПЕРЬ И ДЛЯ ВЛ ТОЖЕ. 04.08 функцию включили только
; для КЛ ("пока сделаем только для КЛ, ВЛ запиши на будущее - это надо
; тестить отдельно"), и в этой шапке было честно записано, что для ВЛ
; она формально тоже ничего не сломала бы. Так и вышло.
;
; Включить её у ВЛ понадобилось ради СОВСЕМ ДРУГОГО - ради количества
; кликов. На длинной прямой ВЛ из десятка опор пользователь вынужден
; был обкликивать каждую пару опор, хотя марка, статус и класс на всём
; участке одни и те же, а данные пролёта от дробления не меняются:
; длина считается по ВСЕМ вершинам между кликами (LEP:SubList +
; LEP:GetSpanLength), опоры в ведомость попадают отдельным сканом
; блоков и от пролётов не зависят. Единственное, что реально терялось
; при клике "первая -> последняя", - это размеры между соседними
; опорами. Посегментные размеры их возвращают: у каждой опоры своя
; вершина маршрута (LEP:InsertVertexOnRoute), значит участок между
; каждой парой соседних опор - отдельный размер.
;
; ⚠️ Что при этом У ВЛ ИЗМЕНИЛОСЬ на обычном покликовом сценарии:
; почти ничего. У пролёта между двумя соседними опорами Verts - это
; ровно две точки, один участок, один размер, как и раньше; сами точки
; те же (символ опоры вставлен РОВНО в вершину, см.
; LEP:PlacePoleOnRoute). Разница появится там, где трасса гнётся МЕЖДУ
; опорами, без опоры на изломе: раньше ВЛ рисовала один размер по
; прямой, то есть МЕНЬШЕ, чем провод реально проходит, - теперь два по
; коленам. Это исправление, а не регресс.
;
; Длина КАЖДОГО участка округляется отдельно, единым правилом проекта
; (LEP:RoundLength, LEP-UTILS.LSP) - это независимые размеры на
; чертеже, каждый должен быть верен сам по себе. ⚠️ Из-за этого сумма
; подписанных участков может отличаться от общей длины в выноске на
; метр-другой (несколько округлений вместо одного) - это нормально и
; неизбежно для любых размеров на чертеже.
;
; ⚠️ ИЗМЕНЕНО 2026-08-05: было LEP:RoundNearest (всегда по математике),
; из-за чего размер расходился с выноской того же пролёта, которая
; округляла вверх. Теперь правило общее. Короткие колена от этого не
; пострадали: они как раз ниже порога и по-прежнему округляются по
; математике - 1,1 м останется "1 м", а не станет "2 м".
;
; Вырожденные участки (после округления 0 м) пропускаются - "0 м" на
; чертеже это мусор. Такое бывает, если в трассе оказались две почти
; совпадающие вершины.
;
; ✅ 2026-08-05: участок пропускается ЕЩЁ И ТОГДА, когда размерная
; линия на этом месте уже есть (LEP:DimensionAlreadyThere ниже) -
; иначе второй маршрут, идущий по общим опорам с первым, рисовал
; размеры поверх уже готовых. Сколько участков пропущено, печатается
; ОДНОЙ строкой в конце.
;=====================================================================

(defun LEP:CreateSpanDimensions (Verts / i P1 P2 SegLen DimSegs Skipped)

    ;; ✅ ДОБАВЛЕНО 2026-08-20: близкие вершины схлопываются в один
    ;; узел ДО того, как что-либо мерить. Иначе вершина, стоящая в
    ;; полуметре от опоры (излом трассы, нарисованный руками, плюс
    ;; вершина самой опоры рядом), даёт лишний размер "1 м" - см.
    ;; подробный разбор в шапке LEP:CollapseDimVertices выше.
    ;; ⚠️ Схлопнутый список живёт ТОЛЬКО внутри этой функции: длина
    ;; пролёта и провод считаются по полному набору вершин.
    (setq Verts (LEP:CollapseDimVertices Verts))

    ;; ✅ ДОБАВЛЕНО 2026-08-05: список уже существующих размерных линий
    ;; собирается ОДИН РАЗ на весь вызов, а не заново на каждый участок.
    ;; Иначе на чертеже с двумя сотнями размеров и десятком участков мы
    ;; бы сделали две тысячи лишних чтений объектов.
    ;;
    ;; ⚠️ Размеры, нарисованные ВНУТРИ этого же вызова, в список не
    ;; попадают - и это правильно: иначе первый участок мог бы задавить
    ;; следующий. Соседние участки одной трассы друг друга не глушат
    ;; (середина следующего лежит ЗА концом предыдущего), так что
    ;; терять тут нечего.
    (setq DimSegs (LEP:CollectExistingDimSegments))
    (setq Skipped 0)

    (setq i 0)

    (while (< i (1- (length Verts)))

        (setq P1 (nth i Verts))
        (setq P2 (nth (1+ i) Verts))
        (setq SegLen (LEP:RoundLength (distance P1 P2)))

        (cond

            ;; Вырожденный участок - "0 м" на чертеже это мусор.
            ((<= SegLen 0) nil)

            ;; На этом месте размерная линия уже есть (общий участок
            ;; двух маршрутов) - второй раз не рисуем.
            ((LEP:DimensionAlreadyThere P1 P2 DimSegs)
                (setq Skipped (1+ Skipped))
            )

            (t (LEP:CreateSpanDimension P1 P2 SegLen))
        )

        (setq i (1+ i))
    )

    ;; Сообщаем ОДНОЙ строкой на весь пролёт, а не на каждый участок -
    ;; на общем участке из десятка опор десять одинаковых сообщений
    ;; были бы шумом. Формулировка без склонения числительного
    ;; намеренно: "участков: 1" читается нормально, а "1 участков" нет.
    (if (> Skipped 0)
        (princ
            (strcat
                "\n[LEP-SPAN] Пропущено участков, где размерная линия уже есть: "
                (itoa Skipped)
            )
        )
    )
)


;=====================================================================
; LEP:CollectExistingDimSegments     (НОВАЯ 2026-08-05)
;
; Собирает геометрию ВСЕХ размерных линий проекта в простой список
; пар точек: ( (A1 B1) (A2 B2) ... ), где A и B - те две точки, между
; которыми размер измеряет расстояние.
;
; Точки берутся из DXF-групп 13 и 14 сущности DIMENSION. ✅ Проверено
; живым тестом в консоли AutoCAD 2026-08-05 (по правилу проекта "не
; полагайся на память о DXF там, где тест дёшев"): клик по размерной
; линии пролёта вернул 0=DIMENSION и две точки в координатах чертежа,
; совпадающие с опорами по краям этого размера.
;
; Сканируется ТОЛЬКО слой *LEP-Layer-Dim* - чужие размеры с подосновы
; или из другой программы нас не касаются, и глушить по ним свои
; размеры было бы неверно.
;=====================================================================

(defun LEP:CollectExistingDimSegments (/ SS i EData A B Result)

    (setq Result nil)

    (setq SS (ssget "_X" (list '(0 . "DIMENSION") (cons 8 *LEP-Layer-Dim*))))

    (if SS
        (progn
            (setq i 0)
            (repeat (sslength SS)
                (setq EData (entget (ssname SS i)))
                (setq A (cdr (assoc 13 EData)))
                (setq B (cdr (assoc 14 EData)))

                ;; Вырожденные и битые пропускаем молча - на них
                ;; проверка всё равно ничего осмысленного не даст.
                (if (and A B (> (distance A B) 1e-9))
                    (setq Result (append Result (list (list A B))))
                )

                (setq i (1+ i))
            )
        )
    )

    Result
)


;=====================================================================
; LEP:DimensionAlreadyThere     (НОВАЯ 2026-08-05)
;
; Отвечает на вопрос "нужен ли размер на участок P1-P2, или он тут уже
; нарисован?". T - уже есть, рисовать не надо.
;
; ЗАЧЕМ (случай пользователя 2026-08-05). Маршрут 2 вливается в
; маршрут 1 и идёт с ним по общим опорам до общей ТП. Пролёт маршрута 1
; уже расставил размеры на этом участке; пролёт маршрута 2 рисовал их
; заново поверх. Единственной защитой от дублей был счётчик пролётов на
; ТОЙ ЖЕ ПАРЕ ОПОР (LEP:FindSamePolePairSpans) - но у двух маршрутов
; пары концов разные ("первая опора маршрута 1 -> ТП" против "первая
; опора маршрута 2 -> ТП"), и он не срабатывал.
;
; ⚠️ ПОЧЕМУ ПРОВЕРЯЕМ НЕ "ЧЕЙ ЭТО ПРОЛЁТ", А "ЕСТЬ ЛИ ТУТ ЛИНИЯ".
; Первым просилось "посмотреть, нет ли размеров у другого маршрута" -
; но чертёж про маршруты ничего не знает: размерная линия это просто
; объект на слое LEP-DIM, без всякой связи с трассой. Проверка по
; месту проще, надёжнее и заодно ловит дубли внутри ОДНОГО маршрута
; (например, если пролёты пересекающихся кликов перекрылись).
;
; ⚠️ ПОЧЕМУ ПО СЕРЕДИНЕ, А НЕ ПО КОНЦАМ. Сравнение концов ловило бы
; только ТОЧНЫЕ дубли. А на общем участке у маршрута 2 вершины стоят
; НЕ на опорах (опоры-то чужие, вершины вставлялись в полилинию
; маршрута 1), а там, где пользователь кликал мышкой, когда рисовал
; полилинию. Его участок обычно ДЛИННЕЕ и накрывает несколько старых
; размеров сразу - концы не совпадают ни с чем, и проверка по концам
; пропустила бы ровно половину случаев. Именно этим и объясняется
; наблюдение пользователя "где-то задвоилось, а где-то нет".
;
; ⚠️ ПОЧЕМУ ЕЩЁ И УГОЛ. Без проверки параллельности мы глушили бы
; размер, который просто ПЕРЕСЕКАЕТ старый под углом (перекрёсток двух
; трасс): его середина случайно оказалась бы на чужой линии. Молча
; потерянный нужный размер хуже, чем лишняя линия, поэтому условия ДВА
; и они должны выполниться ОБА.
;
; ⚠️ ЧЕГО ФУНКЦИЯ НЕ ЛОВИТ (честно): если новый участок перекрывает
; старый размер лишь ЧАСТИЧНО и его середина вышла за пределы старого -
; размер нарисуется. Случай возможен, полностью он не закрыт.
;
; Аргументы:
;   P1, P2  - концы участка, на который собираемся ставить размер;
;   DimSegs - готовый список существующих размеров (пары точек), см.
;             LEP:CollectExistingDimSegments. Передаётся снаружи, чтобы
;             не пересобирать его на каждый участок.
;=====================================================================

;; ⚠️ Seg - переменная foreach, и она тоже должна быть в списке локальных:
;; в AutoLISP область видимости динамическая, необъявленная переменная
;; цикла утекает наружу и может затереть чужую с тем же именем.
(defun LEP:DimensionAlreadyThere (P1 P2 DimSegs / Mid AngNew AngTolRad Found A B Proj AngOld Diff Seg)

    (setq Found nil)

    ;; Угловой допуск в CONFIG хранится в ГРАДУСАХ (так его понятнее
    ;; править), а функция angle работает в РАДИАНАХ - переводим здесь.
    (setq AngTolRad (* pi (/ *LEP-Dim-Duplicate-AngleTol* 180.0)))

    (setq Mid
        (list
            (/ (+ (car P1) (car P2)) 2.0)
            (/ (+ (cadr P1) (cadr P2)) 2.0)
        )
    )
    (setq AngNew (angle P1 P2))

    (foreach Seg DimSegs
        (if (not Found)
            (progn
                (setq A (car Seg))
                (setq B (cadr Seg))

                ;; Условие 1 - середина нового участка лежит НА отрезке
                ;; существующего размера. LEP:ProjectPointOnSegment
                ;; (LEP-POLE.LSP) зажимает проекцию концами отрезка,
                ;; поэтому "рядом с бесконечной прямой, но далеко за
                ;; краем размера" сюда не пройдёт - что и нужно.
                (setq Proj (LEP:ProjectPointOnSegment Mid A B))

                (if (<= (distance Mid Proj) *LEP-Dim-Duplicate-Tolerance*)
                    (progn
                        ;; Условие 2 - параллельность. Направление
                        ;; (кто первый, кто второй) значения не имеет,
                        ;; поэтому разницу углов сводим к диапазону
                        ;; 0..90°: сначала убираем "обход через 360°",
                        ;; затем разворот на 180°.
                        (setq AngOld (angle A B))
                        (setq Diff (abs (- AngNew AngOld)))
                        (if (> Diff pi) (setq Diff (- (* 2.0 pi) Diff)))
                        (if (> Diff (/ pi 2.0)) (setq Diff (- pi Diff)))

                        (if (<= Diff AngTolRad)
                            (setq Found T)
                        )
                    )
                )
            )
        )
    )

    Found
)


;=====================================================================
; LEP:CreateSpanLabel
;
; Подпись-выноска у пролёта: статус + марка провода/кабеля + длина.
; Формат статуса тот же, что у опор (LEP:CreatePoleLabel) - "Проект."
; / "Сущ." - для единообразия подписей на чертеже.
;
; SpanLen - теперь РЕАЛЬНАЯ длина материала с запасом (см.
; LEP:GetRealLength), уже округлённая ВВЕРХ до целого метра, а не
; сырое геометрическое расстояние, как раньше - поэтому выводится
; просто целым числом (itoa), без десятичного разряда.
;=====================================================================

;=====================================================================
; LEP:PluralPipes
;
; Правильная форма слова "труба" для числа N: 1 труба, 2-4 трубы,
; 5-20 труб. Нужна для третьей строки подписи КЛ ("2 трубы 160 мм
; методом ГНБ").
;
; Сейчас число труб в проколе - константа 2 (*LEP-GNB-PipesPerBore*),
; и можно было бы просто написать "трубы" текстом. Но константа на то и
; константа, что её однажды поменяют - и подпись молча станет
; безграмотной ("1 трубы", "5 трубы"). Правило русского языка стоит
; шести строк кода, поэтому лучше сразу.
;
; Правило: смотрим на последние две цифры. 11-14 - всегда "труб"
; (исключение, иначе 11 дало бы "труба"), дальше по последней цифре:
; 1 - "труба", 2-4 - "трубы", остальное - "труб".
;=====================================================================

(defun LEP:PluralPipes (N / Last2 Last1)

    (setq Last2 (rem N 100))
    (setq Last1 (rem N 10))

    (cond
        ((and (>= Last2 11) (<= Last2 14)) "труб")
        ((= Last1 1) "труба")
        ((and (>= Last1 2) (<= Last1 4)) "трубы")
        (t "труб")
    )
)


;=====================================================================
; LEP:GetMethodLabel
;
; Третья строка подписи КЛ - способ прокладки (2026-07-24, просьба
; пользователя). Возвращает готовый текст или nil, если строки быть не
; должно.
;
; ГНБ - ДВЕ строки: "2 трубы 160 мм" / "методом ГНБ" (у подписи КЛ они
; идут третьей и четвёртой). И количество труб
; (*LEP-GNB-PipesPerBore*), и диаметр (*LEP-GNB-PipeDiameter*) берутся
; из CONFIG, а не пишутся текстом - иначе подпись на чертеже разъехалась
; бы с ведомостью при первой же правке числа труб.
;
; Траншея - *LEP-Label-Method-Trench* ("в траншее").
;
; nil (строки нет) - для ВЛ и для СУЩЕСТВУЮЩЕЙ КЛ: у них METHOD в XDATA
; нет вообще (у существующей КЛ способ прокладки не спрашивается - она
; уже проложена как проложена, см. C:LEP-SPAN).
;=====================================================================

(defun LEP:GetMethodLabel (Method)

    (cond
        ((= Method "GNB")
            ;; ⚠️ ДВЕ строки, а не одна (уточнение пользователя
            ;; 2026-07-24): "2 трубы 160 мм" / "методом ГНБ". Разрыв -
            ;; код абзаца MTEXT "\P" (не "\n": это MLEADER/MTEXT, у них
            ;; свой код переноса), тот же приём, что и в остальных
            ;; многострочных подписях проекта.
            (strcat
                (itoa *LEP-GNB-PipesPerBore*) " "
                (LEP:PluralPipes *LEP-GNB-PipesPerBore*) " "
                (itoa *LEP-GNB-PipeDiameter*) " мм"
                "\\P" "методом ГНБ"
            )
        )
        ((= Method "TRENCH") *LEP-Label-Method-Trench*)
        (t nil)
    )
)


;=====================================================================
; LEP:GetLongestSegmentMid     (НОВАЯ 2026-08-06)
;
; Возвращает СЕРЕДИНУ САМОГО ДЛИННОГО ПРЯМОГО УЧАСТКА ломаной - точку,
; к которой цепляется общая подпись пролёта.
;
; ЗАЧЕМ (баг, найденный пользователем 2026-08-06 на тестовой сцене, но
; замеченный им ещё раньше на рабочих чертежах). Раньше подпись
; цеплялась к СЕРЕДИНЕ ПРЯМОЙ между первым и последним концом группы -
; то есть к среднему арифметическому двух координат. На прямом пролёте
; эта точка лежит на линии, и всё выглядело правильно. Но стоит
; маршруту согнуться - и середина отрезка "начало-конец" оказывается
; В СТОРОНЕ ОТ САМОЙ ЛИНИИ, тем дальше, чем круче излом. У маршрута с
; поворотом почти на 90° подпись уезжала в пустоту и висела в воздухе,
; а выноска тянулась к точке, где никакого провода нет.
;
; ПОЧЕМУ ИМЕННО САМЫЙ ДЛИННЫЙ УЧАСТОК, а не середина пути вдоль трассы
; (решение пользователя 2026-08-06). Середина пути тоже всегда лежит на
; линии и этим лучше старого варианта - но на Г-образном маршруте она
; попадает на поворотный кусок, то есть на короткую перемычку сбоку.
; Самый длинный участок - это почти всегда магистральный кусок, и
; подпись садится туда, где её ищут глазами.
;
; ⚠️ Вырожденный случай (меньше двух точек) возвращает первую точку -
; подпись всё равно должна появиться, пусть и не в идеальном месте.
; Молча не создать подпись было бы хуже: пролёт выпал бы из
; объединения групп, и следующий пересчёт его не нашёл бы.
;=====================================================================

(defun LEP:GetLongestSegmentMid (Pts / i A B L BestL BestMid)

    (setq i 0)
    (setq BestL -1.0)
    (setq BestMid nil)

    (while (< i (1- (length Pts)))

        (setq A (nth i Pts))
        (setq B (nth (1+ i) Pts))
        (setq L (distance A B))

        (if (> L BestL)
            (progn
                (setq BestL L)
                (setq BestMid
                    (list
                        (/ (+ (car A) (car B)) 2.0)
                        (/ (+ (cadr A) (cadr B)) 2.0)
                    )
                )
            )
        )

        (setq i (1+ i))
    )

    (if BestMid BestMid (car Pts))
)


(defun LEP:CreateSpanLabel (SubVerts WireName SpanLen Status Method / MidPt TextPt LabelText MethodLine OldLayer StatusText)

    (setq OldLayer (getvar "CLAYER"))
    (LEP:SetCurrentLayer *LEP-Layer-Text*)

    ;; ⚠️ ИЗМЕНЕНО 2026-08-06: было среднее арифметическое первой и
    ;; последней точки - подпись висела в воздухе на любом изогнутом
    ;; маршруте. Подробное обоснование - в шапке LEP:GetLongestSegmentMid
    ;; выше.
    ;; ⚠️ Работает, только если сюда передан ВЕСЬ список вершин группы.
    ;; До этой правки вызывающая сторона передавала ровно ДВЕ точки
    ;; (начало и конец), и промежуточных вершин функция не видела в
    ;; принципе - см. LEP:FinalizeSpanLabel.
    (setq MidPt (LEP:GetLongestSegmentMid SubVerts))

    (setq TextPt
        (list
            (+ (car MidPt) *LEP-LeaderOffset*)
            (+ (cadr MidPt) *LEP-LeaderOffset*)
        )
    )
 
    (if (= Status "EXIST")
        (setq StatusText "Сущ.")
        (setq StatusText "Проект.")
    )

    ;; ⚠️ ФИКС 2026-07-16 (просьба пользователя): "L=... м" переехала
    ;; на ВТОРУЮ строку - код разрыва абзаца MTEXT "\P" (не "\n" -
    ;; это НЕ обычный текст, а MLEADER/MTEXT, там свой код переноса,
    ;; тот же приём, что уже в двухстрочной подписи опоры и в
    ;; дописанной строке ПУ). Запятая-разделитель убрана - вместе с
    ;; переносом строки она была бы не нужна (см. было: "..., L=...").
    (setq LabelText
        (strcat StatusText " " WireName "\\PL=" (itoa SpanLen) " м")
    )

    ;; ✅ ДОБАВЛЕНО 2026-07-24 (просьба пользователя): ТРЕТЬЯ строка -
    ;; способ прокладки КЛ ("2 трубы 160 мм методом ГНБ" / "в траншее").
    ;; Появляется ТОЛЬКО у проектируемой КЛ - у ВЛ и у существующей КЛ
    ;; LEP:GetMethodLabel вернёт nil, и подпись останется двухстрочной,
    ;; ровно как была.
    (setq MethodLine (LEP:GetMethodLabel Method))
    (if MethodLine
        (setq LabelText (strcat LabelText "\\P" MethodLine))
    )
 
    ;; МИГРАЦИЯ 2026-07-15: LEADER -> MLEADER (см. LEP-CONFIG.LSP,
    ;; раздел "СТИЛЬ ВЫНОСОК MLEADER"). Вызов проще, чем у LEADER -
    ;; просто две точки и текст, без "пусто"-ответов на промежуточные
    ;; промпты.
    (command "_.MLEADER" MidPt TextPt LabelText)

    ;; Фон под текстом - свойство КАЖДОЙ выноски отдельно, не стиля
    ;; (см. LEP-CONFIG.LSP, раздел "ФОНОВАЯ МАСКА ТЕКСТА ВЫНОСОК").
    (LEP:SetMLeaderBackgroundMask (entlast))

    ;; Порядок отрисовки - наверх (по просьбе пользователя 2026-07-15,
    ;; см. LEP:BringToFront, LEP-UTILS.LSP).
    (LEP:BringToFront (entlast))

    (setvar "CLAYER" OldLayer)

    ;; ⚠️ ДОБАВЛЕНО 2026-07-22: возвращает саму созданную подпись -
    ;; нужно для объединения подписей соседних пролётов (LABELHANDLE
    ;; в XDATA пролёта, см. LEP:FinalizeSpanLabel ниже) - тот же приём,
    ;; что уже есть у LEP:CreatePoleLabel в LEP-POLE.LSP.
    (entlast)
)


;=====================================================================
; LEP:GetSpanEndpoints
;
; Первая и последняя вершина УЖЕ СОЗДАННОГО объекта-пролёта (LWPOLYLINE) -
; читает геометрию через LEP:GetVertices (LEP-POLYLINE.LSP, общая
; функция для любой LWPOLYLINE), а не хранит SubVerts отдельно. Нужна
; при объединении подписей - чтобы найти крайние точки ВСЕЙ группы
; пролётов, а не только вновь созданного (см. LEP:FinalizeSpanLabel).
;=====================================================================

(defun LEP:GetSpanEndpoints (SpanEnt / V)
    (setq V (LEP:GetVertices SpanEnt))
    (list (car V) (last V))
)


;=====================================================================
; LEP:GetSpanNeighbors
;
; Находит пролёты ЭТОГО ЖЕ маршрута, у которых POLE1HANDLE или
; POLE2HANDLE совпадает с заданным PoleHandle - то есть "соседний
; пролёт, упирающийся в ту же самую опору" (по хендлу, не по
; координатам - см. ⚠️ у LEP:PickPole выше). Сканирует те же 4 слоя
; пролётов (ВЛ+КЛ, Проект.+Сущ.), что и LEP:ReassignRoute
; (LEP-DATA.LSP) - тот же проверенный приём "ssget с слоями через
; запятую в одном фильтре". ExcludeEnt - сам новый пролёт, чтобы не
; найти самого себя соседом.
;
; ⚠️ Старые пролёты (нарисованные ДО этой правки, 2026-07-22) не имеют
; POLE1HANDLE/POLE2HANDLE вообще (LEP:GetDataValue вернёт nil) - они
; просто никогда не совпадут ни с одним PoleHandle и не найдутся
; соседями. Это осознанное ограничение, не баг: объединение подписей
; заработает только между пролётами, созданными ПОСЛЕ этого обновления.
;
; ⚠️ ФИКС 2026-08-03 - ТОЧКА РАЗРЫВА (TRANS) РВЁТ ЦЕПОЧКУ ГНБ.
; ⚠️ УТОЧНЕНО 2026-08-04 - ТОЛЬКО ГНБ. ТРАНШЕЯ ЧЕРЕЗ МАРКЕР
; ОБЪЕДИНЯЕТСЯ.
;
; Если объект, в который упираются оба пролёта, - маркер точки разрыва
; участка (TYPE = "TRANS", LEP-TRANSSYM.LSP), И у пролёта способ
; прокладки "ГНБ" - соседями они НЕ считаются, подписи через маркер не
; объединяются.
;
; Зачем это появилось (03.08): маркер задумывался под смену способа
; прокладки (ГНБ <-> траншея), и там объединение и так не срабатывало -
; METHOD разный (условие в LEP:FinalizeSpanLabel). Но пользователь
; принёс случай, где способ НЕ менялся: прокол ГНБ, потом маркер, потом
; СНОВА прокол ГНБ, но уже под другим углом. Для программы совпало всё
; - марка, статус, способ, - и два ФИЗИЧЕСКИ РАЗНЫХ прокола слиплись в
; одну подпись (а следом и в один прокол в ведомости - трубы там тогда
; считались по общей подписи). Сравнение полей тут не помогает ПО
; ОПРЕДЕЛЕНИЮ: у двух проколов все поля совпадают, разные они не
; данными, а физикой - бур вышел из земли и зашёл заново.
;
; Почему сузили до ГНБ (04.08, решение пользователя): **прокол и
; траншея - разные по природе работы**. Прокол дискретен: вышел бур -
; кончился прокол, нужна своя запасная труба. Траншея - непрерывная
; канава, которую роют руками или трактором; её метраж не зависит от
; того, где мы поставили служебный маркер, и делить подпись незачем.
; Прямая формулировка пользователя: "траншея в отличии от ГНБ это
; просто канава... объединять подпись для общей длины траншеи можно и
; нужно даже если произошла смена участка".
;
; Итоговый инвариант (заменяет более жёсткий от 03.08):
;   **через маркер TRANS не объединяется ГНБ. Всё остальное -
;   объединяется по обычным правилам (совпали марка/статус/способ).**
;
; Способ берём у САМОГО нового пролёта - это и есть ExcludeEnt (в
; LEP:FinalizeSpanLabel сюда всегда передаётся SpanEnt, чью группу мы
; и собираем). Его XDATA записана ДО вызова, так что METHOD уже на
; месте. Проверять обе стороны не нужно: если у соседа способ другой,
; его и так отсеет сравнение METHOD в LEP:FinalizeSpanLabel.
;
; У ВЛ и у существующей КЛ ключа METHOD нет вообще - там nil, условие
; не сработает, маркер для них границей не будет. Это безвредно: ВЛ в
; маркер точки разрыва упереться не может (он ставится на кабельной
; трассе), а если кто-то так сделает - объединение всё равно разрулит
; сравнение марок.
;
; ⚠️ handent с аргументом nil падает с ошибкой, поэтому PoleHandle
; сначала проверяется на существование (у старых пролётов его нет, см.
; абзац выше). На несуществующий хендл (маркер стёрли руками) handent
; вернёт nil - это не ошибка, просто граница не распознается, и пролёты
; поведут себя как раньше.
;=====================================================================

(defun LEP:GetSpanNeighbors (RouteID PoleHandle ExcludeEnt / EndEnt SS i Ent Result)

    (setq Result nil)

    (setq EndEnt (if PoleHandle (handent PoleHandle)))

    (if (and EndEnt
             (= (LEP:GetDataValue EndEnt "TYPE") "TRANS")
             (= (LEP:GetDataValue ExcludeEnt "METHOD") "GNB")
        )

        ;; Маркер + ГНБ = граница прокола, соседей через неё нет.
        ;; Траншея сюда НЕ попадает и ищет соседей как обычно.
        (setq Result nil)

        ;; Обычный конец (опора/КТП/киоск) - ищем соседей как раньше.
        (progn

    (setq SS
        (ssget "_X"
            (list
                '(0 . "LWPOLYLINE")
                (cons 8
                    (strcat
                        *LEP-Layer-Proj-VL* "," *LEP-Layer-Exist-VL* ","
                        *LEP-Layer-Proj-KL* "," *LEP-Layer-Exist-KL*
                    )
                )
            )
        )
    )

    (if SS
        (progn
            (setq i 0)
            (repeat (sslength SS)
                (setq Ent (ssname SS i))
                (if (and (/= Ent ExcludeEnt)
                         (= (LEP:GetDataValue Ent "ROUTE") RouteID)
                         (or (= (LEP:GetDataValue Ent "POLE1HANDLE") PoleHandle)
                             (= (LEP:GetDataValue Ent "POLE2HANDLE") PoleHandle)
                         )
                    )
                    (setq Result (append Result (list Ent)))
                )
                (setq i (1+ i))
            )
        )
    )

        ) ; конец progn "обычный конец"
    ) ; конец if "это граница прокола?"

    Result
)


;=====================================================================
; LEP:FindGroupMembers
;
; Все пролёты ЭТОГО ЖЕ маршрута, у которых LABELHANDLE совпадает с
; заданным - то есть ВСЯ текущая группа пролётов, объединённых под
; одной общей подписью (может быть всего один пролёт, если он ещё ни
; с кем не сливался). Тот же приём сканирования, что и в
; LEP:GetSpanNeighbors выше.
;=====================================================================

(defun LEP:FindGroupMembers (LabelHandle RouteID / SS i Ent Result)

    (setq Result nil)
    (if LabelHandle
        (progn
            (setq SS
                (ssget "_X"
                    (list
                        '(0 . "LWPOLYLINE")
                        (cons 8
                            (strcat
                                *LEP-Layer-Proj-VL* "," *LEP-Layer-Exist-VL* ","
                                *LEP-Layer-Proj-KL* "," *LEP-Layer-Exist-KL*
                            )
                        )
                    )
                )
            )
            (if SS
                (progn
                    (setq i 0)
                    (repeat (sslength SS)
                        (setq Ent (ssname SS i))
                        (if (and (= (LEP:GetDataValue Ent "ROUTE") RouteID)
                                 (= (LEP:GetDataValue Ent "LABELHANDLE") LabelHandle)
                            )
                            (setq Result (append Result (list Ent)))
                        )
                        (setq i (1+ i))
                    )
                )
            )
        )
    )
    Result
)


;=====================================================================
; LEP:FinalizeSpanLabel
;
; ОРКЕСТРАЦИЯ объединения подписей (по просьбе пользователя 2026-07-22:
; "подписывать не каждый пролёт, а целиком линию трассы, если тип
; прокладки не меняется"). Вызывается ПОСЛЕ того, как новый пролёт
; SpanEnt уже создан и его начальная XDATA (без LABELHANDLE) уже
; записана.
;
; Механизм ("как программа распознаёт, что пролёты надо объединить" -
; вопрос пользователя, ответ ниже):
;   1. Ищем СОСЕДНИЕ пролёты этого маршрута с ОБЕИХ сторон нового
;      пролёта (LEP:GetSpanNeighbors, по хендлам опор P1/P2 - НАДЁЖНО,
;      не зависит от порядка, в котором пользователь кликает пролёты:
;      хоть по порядку вдоль трассы, хоть вразнобой, хендл опоры один
;      и тот же в любом случае).
;   2. Из найденных соседей оставляем только те, у которых СОВПАДАЮТ
;      марка провода/кабеля (WIRE), статус (STATUS) И СПОСОБ ПРОКЛАДКИ
;      (METHOD, ГНБ/траншея - ⚠️ добавлено 2026-07-24) - "тип прокладки
;      не меняется", как и просил пользователь. Сравнение WIRE уже
;      само по себе разделяет ВЛ/КЛ (марки ВЛ и КЛ никогда не совпадают
;      текстом), а вот ГНБ и траншея - ОДНА И ТА ЖЕ марка кабеля, их
;      разделяет только METHOD.
;      ⚠️ Ещё исключаются "близнецы" - соседи, у которых совпадают ОБА
;      конца (второй кабель/провод между той же парой объектов): они
;      идут не цепочкой, а параллельно, складывать их длины нельзя.
;   3. Для КАЖДОГО подходящего соседа поднимаем ЕГО ТЕКУЩУЮ группу
;      целиком (LEP:FindGroupMembers по его LABELHANDLE) - это и есть
;      правильный ответ на "а если сосед уже был частью большой уже
;      объединённой группы": группа подхватывается целиком, а не
;      только один сосед. Если новый пролёт совпал ОДНОВременно с
;      левой И правой стороны (мостик между двумя старыми группами) -
;      обе группы автоматически объединяются в одну, т.к. просто
;      складываются в один общий список.
;   4. Все старые подписи (по уникальным LABELHANDLE участников) -
;      удаляются.
;   5. Считается ИТОГОВАЯ длина для новой общей подписи - см. отдельно
;      для ВЛ и КЛ ниже (RawTotal то же самое, что заменяет игра
;      запаса/без запаса, о которой уже договорились).
;   6. Крайние точки группы находятся через индекс вершины вдоль
;      маршрута (LEP:GetNearestVertexIndex) - середина считается
;      именно между ГЕОГРАФИЧЕСКИ крайними точками группы, а не как
;      попало по порядку создания.
;   7. Новая ОБЩАЯ подпись создаётся один раз (LEP:CreateSpanLabel),
;      её LABELHANDLE прописывается ВСЕМ пролётам группы (включая
;      новый) через LEP:SetSpanLabelHandle.
;
; ДЛИНА НА ЧЕРТЕЖЕ vs ДЛИНА В ВЕДОМОСТИ
; (✅ ОКОНЧАТЕЛЬНО СФОРМУЛИРОВАНО 2026-07-24 пользователем):
;
;   НА ЧЕРТЕЖЕ - только ФИЗИКА, без единого запаса на закупку:
;     ВЛ - сырая длина (сумма RAWLENGTH участников);
;     КЛ - сырая длина ПЛЮС метры концевых заделок (сумма RESERVE всех
;          пролётов группы). Эти метры - НЕ запас, а реальный кусок
;          кабеля, который лезет на опору, поэтому на чертеже он
;          остаётся (уточнение пользователя от 2026-07-22, в силе).
;          У наземных концов (КТП/киоск) их сейчас ноль - см.
;          LEP:GetEndReserve.
;
;   В ВЕДОМОСТИ (XDATA LENGTH, LEP-REPORT) - всё остальное: процент
;   на провис/укладку и множитель фаз у 10/6 кВ (LEP:GetRealLength).
;   Подпись этих чисел НЕ показывает вообще.
;
; ⚠️ ИЗМЕНЕНО 2026-07-24: раньше подпись КЛ брала готовую сумму LENGTH
; участников, и после появления процентов запаса у КЛ (2%/4%) эти
; проценты вылезли бы прямо на чертёж. Теперь подпись НЕ смотрит на
; LENGTH вообще - обе величины считаются от RAWLENGTH через
; LEP:GetDisplayLength (общая формула "что показываем на чертеже",
; см. её шапку выше в этом файле). Побочный эффект: округление до
; целого метра теперь делается ОДИН раз на всю группу, а не отдельно
; у каждого пролёта - число может отличаться от старого на метр-два,
; это нормально и даже честнее (меньше накопленных "хвостиков").
;
; Verts - вершины маршрута, нужны, чтобы определить порядок пролётов
; вдоль трассы (см. п.6 выше).
;=====================================================================

(defun LEP:FinalizeSpanLabel (SpanEnt Verts P1Handle P2Handle TypeCode WireName Status / Method Neighbors N NP1 NP2 IsTwin MatchGroup AllMembers M OldHandles H OldEnt RawTotal ReserveTotal RStr Pt Idx BestIdx BestPt WorstIdx WorstPt GroupFirst GroupLast GroupVerts NewLabelEnt NewLabelHandle DisplayLen)

    ;; Способ прокладки берём из XDATA самого пролёта, а не отдельным
    ;; аргументом: XDATA пролёта записывается ДО вызова этой функции,
    ;; и так же она доступна при ремонте подписей (C:LEP-SPAN-REPAIR),
    ;; где никакого "текущего выбора пользователя" вообще нет.
    (setq Method (LEP:GetDataValue SpanEnt "METHOD"))

    (setq Neighbors
        (append
            (LEP:GetSpanNeighbors (LEP:GetDataValue SpanEnt "ROUTE") P1Handle SpanEnt)
            (LEP:GetSpanNeighbors (LEP:GetDataValue SpanEnt "ROUTE") P2Handle SpanEnt)
        )
    )

    ;; Оставляем только соседей с той же маркой и статусом ("тип
    ;; прокладки не меняется").
    ;;
    ;; ⚠️ ФИКС 2026-07-24 - ПАРАЛЛЕЛЬНЫЕ БЛИЗНЕЦЫ НЕ ОБЪЕДИНЯЮТСЯ.
    ;; Объединение подписей задумано для пролётов, идущих ЦЕПОЧКОЙ:
    ;; они делят РОВНО ОДИН общий конец (конец предыдущего = начало
    ;; следующего), и сложить их длины в одну подпись - правильно.
    ;; Но LEP:GetSpanNeighbors считает соседом любого, кто делит ХОТЯ
    ;; БЫ ОДИН хендл - под это определение попадает и ВТОРОЙ ПРОВОД
    ;; (или второй кабель) между ТОЙ ЖЕ парой концов: у него совпадают
    ;; ОБА хендла, и марка со статусом у него, как правило, те же.
    ;; Результат: два кабеля по 30 м между КТП и киоском слились бы в
    ;; одну подпись "60 м" вместо двух подписей по 30 м - как будто
    ;; проложили один длинный кабель. Ровно этот случай пользователь и
    ;; принёс 2026-07-24 (два кабеля 0,4 кВ от КТП до киоска), и он же
    ;; был бы у двух проводов на одной паре опор - механику
    ;; параллельного сдвига (2026-07-22) вживую так и не прогнали,
    ;; поэтому баг до сих пор не всплывал.
    ;;
    ;; Признак близнеца - совпадают ОБА конца (в любом порядке: пролёт
    ;; мог быть нарисован от второго конца к первому). Такие из группы
    ;; исключаются - каждый получает СВОЮ подпись, что и правильно:
    ;; это физически разные кабели, их и заказывают, и монтируют
    ;; отдельно.
    (setq MatchGroup nil)
    (foreach N Neighbors
        (setq NP1 (LEP:GetDataValue N "POLE1HANDLE"))
        (setq NP2 (LEP:GetDataValue N "POLE2HANDLE"))
        (setq IsTwin
            (or (and (= NP1 P1Handle) (= NP2 P2Handle))
                (and (= NP1 P2Handle) (= NP2 P1Handle))
            )
        )
        ;; ⚠️ ФИКС 2026-07-24: СПОСОБ ПРОКЛАДКИ тоже должен совпадать.
        ;; В шапке этой проверки с самого начала было написано "тип
        ;; прокладки не меняется", но сравнивались только марка и
        ;; статус. Для пары ВЛ/КЛ этого хватало случайно - марки
        ;; провода и кабеля никогда не совпадают текстом. А вот ГНБ и
        ;; траншея - ОДНА И ТА ЖЕ марка кабеля, и два соседних пролёта
        ;; "прокол, потом траншея" молча слиплись бы в одну подпись с
        ;; общей длиной. Это ровно тот случай, ради которого 2026-07-24
        ;; и появилась точка смены способа прокладки: делить участок
        ;; надвое, а потом склеивать подписи обратно - бессмысленно, да
        ;; и выглядело бы дико (одна подпись поверх двух линий разного
        ;; цвета, лежащих на разных слоях).
        ;; У ВЛ и у существующей КЛ METHOD в XDATA нет вообще - там с
        ;; обеих сторон nil, а (= nil nil) в AutoLISP даёт истину,
        ;; поэтому для них ничего не меняется.
        (if (and (= (LEP:GetDataValue N "WIRE") WireName)
                 (= (LEP:GetDataValue N "STATUS") Status)
                 (= (LEP:GetDataValue N "METHOD") Method)
                 (not IsTwin)
                 (not (member N MatchGroup))
            )
            (setq MatchGroup (append MatchGroup (list N)))
        )
    )

    ;; Полный список участников итоговой группы: новый пролёт + ВСЕ
    ;; участники текущих групп каждого подходящего соседа (не только
    ;; сами соседи - см. п.3 в шапке функции).
    (setq AllMembers (list SpanEnt))
    (foreach N MatchGroup
        (foreach M (LEP:FindGroupMembers (LEP:GetDataValue N "LABELHANDLE") (LEP:GetDataValue SpanEnt "ROUTE"))
            (if (not (member M AllMembers))
                (setq AllMembers (append AllMembers (list M)))
            )
        )
        ;; На случай, если у соседа ЕЩЁ не было своего LABELHANDLE
        ;; (не должно случаться для пролётов, созданных этой же
        ;; версией кода, но подстраховка не помешает).
        (if (not (member N AllMembers))
            (setq AllMembers (append AllMembers (list N)))
        )
    )

    ;; Удаляем все СТАРЫЕ подписи участников (уникальные хендлы -
    ;; несколько участников уже объединённой группы делят один и тот
    ;; же LABELHANDLE, удалять его дважды не нужно).
    (setq OldHandles nil)
    (foreach M AllMembers
        (setq H (LEP:GetDataValue M "LABELHANDLE"))
        (if (and H (not (member H OldHandles)))
            (setq OldHandles (append OldHandles (list H)))
        )
    )
    (foreach H OldHandles
        (setq OldEnt (handent H))
        (if OldEnt (entdel OldEnt))
    )

    ;; Итоговая длина для подписи - см. подробное обоснование в шапке
    ;; функции. Считается ТОЛЬКО от сырых длин участников (RAWLENGTH),
    ;; в XDATA LENGTH мы здесь принципиально не заглядываем: там сидят
    ;; запасы для ведомости, которым на чертеже делать нечего.
    ;;
    ;; ⚠️ 2026-07-24: метры концевых заделок КЛ тоже суммируются - но
    ;; из ключа RESERVE КАЖДОГО пролёта, а не как "число пролётов x
    ;; константа". После перехода на поконцовый расчёт запас у разных
    ;; пролётов одной группы может отличаться (КТП-опора = 3 м, а
    ;; следующий опора-опора = 6 м), и умножение на количество давало
    ;; бы неверную сумму.
    ;; Если RESERVE нет (пролёт от старой версии программы) - берём
    ;; прежнее поведение, 2 конца-опоры: до 2026-07-24 концом пролёта
    ;; могла быть ТОЛЬКО опора, так что это не догадка, а точное
    ;; воспроизведение того, что там и было.
    (setq RawTotal 0.0)
    (setq ReserveTotal 0.0)
    (foreach M AllMembers
        (setq RawTotal (+ RawTotal (atof (LEP:GetDataValue M "RAWLENGTH"))))
        (setq RStr (LEP:GetDataValue M "RESERVE"))
        (setq ReserveTotal
            (+ ReserveTotal
               (if RStr (atof RStr) (* 2.0 *LEP-KL-Reserve-Pole*))
            )
        )
    )
    ;; ⚠️ 2026-08-05: было LEP:RoundUp, стало LEP:RoundLength - единое
    ;; правило округления длин на весь проект (выше порога вверх, ниже
    ;; по математике). Именно ЭТО число пользователь сравнил с
    ;; размерной линией и увидел расхождение в метр: 46,4958 м дало
    ;; здесь "47", а в размере "46". Теперь обе величины считает одна
    ;; и та же функция, разъехаться они больше не могут.
    (setq DisplayLen
        (LEP:RoundLength
            (LEP:GetDisplayLength TypeCode RawTotal ReserveTotal)
        )
    )

    ;; Крайние точки группы - по индексу вершины вдоль маршрута
    ;; (LEP:GetNearestVertexIndex), не по порядку создания пролётов.
    (setq BestIdx nil)
    (setq WorstIdx nil)
    (foreach M AllMembers
        (foreach Pt (LEP:GetSpanEndpoints M)
            (setq Idx (LEP:GetNearestVertexIndex Verts Pt))
            (if (or (not BestIdx) (< Idx BestIdx))
                (progn (setq BestIdx Idx) (setq BestPt Pt))
            )
            (if (or (not WorstIdx) (> Idx WorstIdx))
                (progn (setq WorstIdx Idx) (setq WorstPt Pt))
            )
        )
    )
    (setq GroupFirst BestPt)
    (setq GroupLast WorstPt)

    ;; Method здесь - способ прокладки, прочитанный из XDATA самого
    ;; пролёта в начале функции. Все участники группы гарантированно
    ;; имеют ТОТ ЖЕ способ: с 2026-07-24 METHOD входит в условие
    ;; объединения (см. выше), поэтому подпись с "методом ГНБ" физически
    ;; не может накрыть траншейный участок.
    ;; ⚠️ ИЗМЕНЕНО 2026-08-06: передаём ВЕСЬ участок вершин группы
    ;; (LEP:SubList между крайними индексами), а не две крайние точки.
    ;; Раньше сюда уходило ровно (GroupFirst GroupLast) - и подпись
    ;; физически не могла сесть на линию: промежуточных вершин функция
    ;; не видела, и ей оставалось только усреднить две координаты.
    ;; На изогнутом маршруте такая "середина" оказывается в стороне от
    ;; линии, и подпись висит в воздухе.
    ;;
    ;; Подстраховка на вырожденный случай: если по индексам получилось
    ;; меньше двух точек (BestIdx = WorstIdx - обе крайние точки группы
    ;; сели на одну вершину), берём прежние две точки. Подпись при этом
    ;; встанет как раньше - хуже, но она БУДЕТ. Молча остаться без
    ;; подписи нельзя: пролёт выпал бы из объединения групп.
    (setq GroupVerts (LEP:SubList Verts BestIdx WorstIdx))
    (if (< (length GroupVerts) 2)
        (setq GroupVerts (list GroupFirst GroupLast))
    )

    (setq NewLabelEnt (LEP:CreateSpanLabel GroupVerts WireName DisplayLen Status Method))
    (setq NewLabelHandle (cdr (assoc 5 (entget NewLabelEnt))))

    (foreach M AllMembers
        (LEP:SetSpanLabelHandle M NewLabelHandle)
    )
)


;=====================================================================
; LEP:AddKLPoleNote
;
; Дописывает "+ подъём кабеля по опоре" в подпись опоры (PoleEnt) - по
; просьбе пользователя 2026-07-22: если пролёт между двумя опорами -
; КЛ, автоматически добавлять эту фразу к подписям ОБЕИХ опор (через
; LEP:AppendMLeaderText, тот же приём, что уже используется для
; "+ проект. ПУ" в LEP-END.LSP).
;
; ⚠️ Защита от дублирования: опора может стоять на стыке ДВУХ КЛ-
; пролётов подряд (кабель идёт через неё насквозь) - тогда функция
; вызовется для неё дважды, по разу от каждого соседнего пролёта.
; Перед дописыванием проверяем текст ТЕКУЩЕЙ подписи опоры
; (vl-string-search) - если фраза там уже есть, ничего не делаем.
;=====================================================================

(defun LEP:AddKLPoleNote (PoleEnt / LabelHandle LabelEnt LabelText)

    ;; ⚠️ ДОБАВЛЕНО 2026-07-24: только НАСТОЯЩИЕ опоры. С этого дня
    ;; концом кабельного пролёта может быть КТП или кабельный киоск -
    ;; а фраза "подъём кабеля по опоре" на наземной подстанции просто
    ;; неверна: кабель туда заходит внизу, никуда не поднимаясь.
    ;;
    ;; ⚠️ Проверка нужна ИМЕННО СЕЙЧАС, хотя прямо сегодня она ничего
    ;; не меняет: у КТП/киоска в XDATA нет ключа LABELHANDLE, поэтому
    ;; функция и так молча ничего не делала. Но это везение, а не
    ;; замысел - как только у них появится LABELHANDLE (а он нужен,
    ;; иначе подпись осиротеет при удалении объекта, ровно как было с
    ;; опорами), на подстанции вылезла бы фраза про подъём по опоре.
    (if (/= (LEP:GetDataValue PoleEnt "TYPE") "POLE")
        (setq LabelHandle nil)
        (setq LabelHandle (LEP:GetDataValue PoleEnt "LABELHANDLE"))
    )

    (if LabelHandle
        (progn
            (setq LabelEnt (handent LabelHandle))
            (if LabelEnt
                (progn
                    (setq LabelText (cdr (assoc 304 (entget LabelEnt))))
                    (if (not (vl-string-search "подъём кабеля" LabelText))
                        (LEP:AppendMLeaderText LabelEnt "+ подъём кабеля по опоре")
                    )
                )
            )
        )
    )
)


;=====================================================================
; LEP:FindRouteByID
;
; Находит ENAME полилинии маршрута по её ID (например "LEP_ROUTE_01") -
; сканирует служебный слой маршрутов (*LEP-Layer-Route*), тот же приём
; "временно включить слой на время поиска, если был выключен", что уже
; используется в LEP:GetMaxRouteNumber/LEP:FindNearestRoute
; (LEP-DATA.LSP/LEP-POLE.LSP) - слой маршрутов обычно скрыт
; (LEP-ROUTEVIS), ssget без явного включения ничего бы на нём не увидел.
;
; ⚠️ ФИКС 2026-07-22 (по просьбе пользователя - убрать лишний клик по
; маршруту в C:LEP-SPAN): раньше пользователь выбирал маршрут САМ
; кликом (и для этого должен был не забыть включить LEP-ROUTEVIS) -
; теперь C:LEP-SPAN находит маршрут САМ по ID, который уже хранится в
; XDATA выбранной опоры (ключ ROUTE, LEP:AddPoleData) - видимость слоя
; маршрута для этого поиска не имеет значения, эта функция сама
; включает его на время сканирования и возвращает как было.
;
; Возвращает ename маршрута, либо nil, если трасса с таким ID не
; найдена на чертеже.
;=====================================================================

(defun LEP:FindRouteByID (RouteID / LayerData WasOff SS i Ent Found)

    (setq Found nil)

    (setq LayerData (tblsearch "LAYER" *LEP-Layer-Route*))
    (setq WasOff (and LayerData (< (cdr (assoc 62 LayerData)) 0)))
    (if WasOff
        (command "_.-layer" "_On" *LEP-Layer-Route* "")
    )

    (setq SS (ssget "_X" (list '(0 . "LWPOLYLINE") (cons 8 *LEP-Layer-Route*))))
    (if SS
        (progn
            (setq i 0)
            (repeat (sslength SS)
                (setq Ent (ssname SS i))
                (if (= (LEP:GetDataValue Ent "ID") RouteID)
                    (setq Found Ent)
                )
                (setq i (1+ i))
            )
        )
    )

    (if (and WasOff (/= (getvar "CLAYER") *LEP-Layer-Route*))
        (command "_.-layer" "_Off" *LEP-Layer-Route* "")
    )

    Found
)


;=====================================================================
; LEP:FindRoutesThroughPoints
;
; ✅ ДОБАВЛЕНО 2026-07-22 (по просьбе пользователя). Находит ВСЕ
; маршруты на чертеже, чья полилиния проходит РЯДОМ С ОБЕИМИ точками
; P1/P2 (в пределах *LEP-Route-Detect-Tolerance*, LEP-CONFIG.LSP).
;
; ЗАЧЕМ: у опоры в XDATA записан ТОЛЬКО тот маршрут, которым её
; СОЗДАЛИ (ключ ROUTE, LEP:AddPoleData) - навсегда. Если пользователь
; позже проложил ВТОРОЙ маршрут ПОВЕРХ тех же опор (общий участок,
; дальше расходятся - реальный сценарий: "от одной МТП идут в два
; разных места отдельные фидеры"), опора об этом ничего не знает, и
; LEP-SPAN, механически копируя ROUTE с опоры, отнёс бы новый пролёт
; к маршруту 1 - независимо от того, что имел в виду пользователь.
; Программа физически не может "догадаться" по данным опоры. Но
; информация ЕСТЬ В ГЕОМЕТРИИ: полилиния маршрута 2 реально проходит
; через эти точки - её и ищем.
;
; Слой маршрутов обычно СКРЫТ (LEP-ROUTEVIS) - временно включаем на
; время сканирования и возвращаем как было, тот же приём, что в
; LEP:FindRouteByID/LEP:GetMaxRouteNumber/LEP:FindNearestRoute.
;
; Расстояние от точки до полилинии считается через уже готовую
; LEP:FindNearestSegment (LEP-POLE.LSP) - она возвращает ближайшую
; точку НА линии, дальше обычный distance. Никакой новой геометрии.
;
; Возвращает список ename маршрутов-кандидатов (может быть пустым).
;=====================================================================

(defun LEP:FindRoutesThroughPoints (P1 P2 / LayerData WasOff SS i Ent Verts N1 N2 Result)

    (setq Result nil)

    (setq LayerData (tblsearch "LAYER" *LEP-Layer-Route*))
    (setq WasOff (and LayerData (< (cdr (assoc 62 LayerData)) 0)))
    (if WasOff
        (command "_.-layer" "_On" *LEP-Layer-Route* "")
    )

    (setq SS (ssget "_X" (list '(0 . "LWPOLYLINE") (cons 8 *LEP-Layer-Route*))))

    (if SS
        (progn
            (setq i 0)
            (repeat (sslength SS)
                (setq Ent (ssname SS i))
                (setq Verts (LEP:GetVertices Ent))

                ;; Полилиния меньше 2 вершин - вырожденная (см. защиту в
                ;; C:LEP-ROUTE), LEP:FindNearestSegment на ней работать
                ;; не сможет - пропускаем, а не падаем.
                (if (>= (length Verts) 2)
                    (progn
                        (setq N1 (cadr (LEP:FindNearestSegment Verts P1)))
                        (setq N2 (cadr (LEP:FindNearestSegment Verts P2)))
                        (if (and (< (distance P1 N1) *LEP-Route-Detect-Tolerance*)
                                 (< (distance P2 N2) *LEP-Route-Detect-Tolerance*)
                            )
                            (setq Result (append Result (list Ent)))
                        )
                    )
                )
                (setq i (1+ i))
            )
        )
    )

    (if (and WasOff (/= (getvar "CLAYER") *LEP-Layer-Route*))
        (command "_.-layer" "_Off" *LEP-Layer-Route* "")
    )

    Result
)


;=====================================================================
; LEP:ChooseRouteFromCandidates
;
; Выбор одного маршрута из нескольких кандидатов (см.
; LEP:FindRoutesThroughPoints выше) - показывает их ID списком через
; общую LEP:ChooseFromList (LEP-UTILS.LSP, тот же номерной выбор, что
; и у марок провода/типов опор).
;
; Возвращает ename выбранного маршрута, либо nil при отмене (Enter).
;=====================================================================

(defun LEP:ChooseRouteFromCandidates (Candidates / ItemList Ent ID Choice i)

    (setq ItemList nil)
    (setq i 0)
    (foreach Ent Candidates
        (setq ID (LEP:GetDataValue Ent "ID"))
        (if (not ID) (setq ID "БЕЗ_ID"))
        ;; Значение пары - НОМЕР по порядку (строкой), а не сам ename:
        ;; LEP:ChooseFromList возвращает пару целиком, ename достанем
        ;; по этому номеру из исходного списка Candidates ниже.
        (setq ItemList (append ItemList (list (cons ID (itoa i)))))
        (setq i (1+ i))
    )

    (setq Choice (LEP:ChooseFromList ItemList "Через эти опоры проходит НЕСКОЛЬКО маршрутов - к какому отнести пролёт"))

    (if Choice
        (nth (atoi (cdr Choice)) Candidates)
    )
)


;=====================================================================
; LEP:GetSpanTypeCode
;
; "VL" или "KL" по СЛОЮ уже существующего пролёта - нужно для
; C:LEP-SPAN-REPAIR ниже, где TypeCode неоткуда взять из диалога (в
; отличие от C:LEP-SPAN - там он известен из только что заданного
; вопроса "Тип прокладки"). В XDATA самого пролёта TypeCode отдельным
; ключом не хранится (WIRE/SECTION хранят марку, а не VL/КЛ явно) -
; зато слой у ВЛ и КЛ всегда разный, надёжный признак.
;=====================================================================

(defun LEP:GetSpanTypeCode (Ent / Lyr)
    (setq Lyr (cdr (assoc 8 (entget Ent))))
    (if (or (= Lyr *LEP-Layer-Proj-KL-GNB*)
            (= Lyr *LEP-Layer-Proj-KL-Trench*)
            (= Lyr *LEP-Layer-Exist-KL*)
        )
        "KL"
        "VL"
    )
)


;=====================================================================
; LEP:FindSamePolePairSpans
;
; Находит ВСЕ уже существующие пролёты между ТОЙ ЖЕ парой опор
; (P1Handle/P2Handle, в любом порядке) - неважно, какому маршруту они
; принадлежат. Нужна для параллельного сдвига (см. шапку
; *LEP-Span-ParallelOffset* в CONFIG): несколько проводов на одном и
; том же участке (общие опоры двух маршрутов, или просто вторая марка
; на том же маршруте) без сдвига легли бы точно друг на друга.
;
; Сканирует те же 4 слоя пролётов, что и LEP:GetSpanNeighbors выше -
; но, в отличие от неё, требует совпадения ОБЕИХ опор сразу (не одной
; любой стороны) - это другой признак: не "сосед по трассе", а
; "буквально та же пара опор".
;=====================================================================

(defun LEP:FindSamePolePairSpans (P1Handle P2Handle / SS i Ent EntP1 EntP2 Result)

    (setq Result nil)

    (setq SS
        (ssget "_X"
            (list
                '(0 . "LWPOLYLINE")
                (cons 8
                    (strcat
                        *LEP-Layer-Proj-VL* "," *LEP-Layer-Exist-VL* ","
                        *LEP-Layer-Proj-KL* "," *LEP-Layer-Exist-KL*
                    )
                )
            )
        )
    )

    (if SS
        (progn
            (setq i 0)
            (repeat (sslength SS)
                (setq Ent (ssname SS i))
                (setq EntP1 (LEP:GetDataValue Ent "POLE1HANDLE"))
                (setq EntP2 (LEP:GetDataValue Ent "POLE2HANDLE"))
                (if (or (and (= EntP1 P1Handle) (= EntP2 P2Handle))
                        (and (= EntP1 P2Handle) (= EntP2 P1Handle))
                    )
                    (setq Result (append Result (list Ent)))
                )
                (setq i (1+ i))
            )
        )
    )

    Result
)


;=====================================================================
; LEP:GetParallelOffset
;
; Величина и знак сдвига (метры, со знаком) для N-го по счёту пролёта
; на одной и той же паре опор (N = сколько таких пролётов уже
; существует ДО этого нового - см. LEP:FindSamePolePairSpans выше).
; Поочерёдно в разные стороны от центра, шаг *LEP-Span-ParallelOffset*
; (по просьбе пользователя): N=0 (первый пролёт на этой паре опор) -
; 0.0 (без сдвига, остаётся "на месте"); N=1 -> +1 шаг; N=2 -> -1 шаг;
; N=3 -> +2 шага; N=4 -> -2 шага, и т.д. (нечётный N - сторона "+",
; чётный - сторона "-"; число шагов = "потолок" N/2 - у нечётного и
; чётного N это одно и то же целочисленное выражение (N+1)/2 при
; целочисленном делении, отдельная ветка не нужна).
;=====================================================================

(defun LEP:GetParallelOffset (N / Steps Side)
    (if (= N 0)
        0.0
        (progn
            (setq Steps (/ (+ N 1) 2)) ; целочисленное деление - "потолок" N/2
            (setq Side (if (= (rem N 2) 1) 1.0 -1.0))
            (* Side Steps *LEP-Span-ParallelOffset*)
        )
    )
)


;=====================================================================
; LEP:CollectExistingSpans     (НОВАЯ 2026-08-06)
;
; Собирает геометрию ВСЕХ уже нарисованных пролётов (ВЛ и КЛ, любого
; статуса) в список списков вершин: ( (verts1) (verts2) ... ).
;
; Нужна для посегментного параллельного сдвига: чтобы понять, сколько
; проводов уже идёт по этому месту, надо знать, где они лежат.
; Собирается ОДИН РАЗ на весь пролёт, а не заново на каждый отрезок -
; тот же приём и по той же причине, что в LEP:CreateSpanDimensions.
;
; ⚠️ Собираются пролёты ВСЕХ статусов, не только проектируемые:
; существующая линия занимает место на чертеже ровно так же, как
; проектируемая, и новый провод обязан её обойти.
;=====================================================================

(defun LEP:CollectExistingSpans (/ SS i Ent Verts Result)

    (setq Result nil)

    (setq SS
        (ssget "_X"
            (list
                '(0 . "LWPOLYLINE")
                (cons 8
                    (strcat
                        *LEP-Layer-Proj-VL* "," *LEP-Layer-Exist-VL* ","
                        *LEP-Layer-Proj-KL* "," *LEP-Layer-Exist-KL*
                    )
                )
            )
        )
    )

    (if SS
        (progn
            (setq i 0)
            (repeat (sslength SS)
                (setq Ent (ssname SS i))
                (setq Verts (LEP:GetVertices Ent))
                (if (>= (length Verts) 2)
                    (setq Result (append Result (list Verts)))
                )
                (setq i (1+ i))
            )
        )
    )

    Result
)


;=====================================================================
; LEP:CountOverlappingSpans     (НОВАЯ 2026-08-06)
;
; Сколько уже нарисованных пролётов проходит ПО ЭТОМУ ЖЕ МЕСТУ, что и
; отрезок P1-P2. Это и есть номер параллельного сдвига для отрезка.
;
; ЗАЧЕМ ЗАМЕНИЛА ПРОВЕРКУ ПО ХЕНДЛАМ. Раньше считалось совпадение ПАРЫ
; ХЕНДЛОВ ОПОР (LEP:FindSamePolePairSpans): сколько пролётов имеют те
; же две концевые опоры. Это работало для случая, под который и
; писалось, - два провода между ОДНОЙ И ТОЙ ЖЕ парой опор. Но у двух
; маршрутов, которые совпадают ЧАСТИЧНО (маршрут 2 вливается в маршрут
; 1 и идёт с ним до общей ТП), пары концов РАЗНЫЕ: "первая опора
; маршрута 1 -> ТП" против "первая опора маршрута 2 -> ТП". Совпадение
; не находилось, сдвиг не срабатывал, провода ложились друг на друга -
; поймано пользователем на живом чертеже 2026-08-05. Проверка по
; хендлам умеет отвечать только "та же пара / не та же" и частичное
; перекрытие не видит в принципе, сколько её ни чини.
;
; ⚠️ СЧИТАЕТСЯ ДЛЯ КАЖДОГО ОТРЕЗКА ОТДЕЛЬНО, а не на весь пролёт. В
; этом весь смысл: у маршрута 2 своя улица должна остаться на месте
; (там он один), а общий с маршрутом 1 участок - уехать вбок. Одно
; число на весь пролёт этого не умеет. Заодно решается случай, до
; которого мы бы иначе дошли позже: маршрут 3 может перекрываться с
; маршрутом 1 на одном куске и с маршрутом 2 на другом, и сдвиг ему
; нужен РАЗНЫЙ на этих кусках.
;
; ⚠️ Правило перекрытия ТО ЖЕ, что у дублей размерных линий
; (LEP:DimensionAlreadyThere): середина нашего отрезка лежит на чужом
; отрезке И отрезки параллельны. Оба условия обязательны - без угла мы
; считали бы "своим" провод, который просто ПЕРЕСЕКАЕТ наш под углом
; на перекрёстке трасс, и сдвигали бы линию без всякой причины.
;
; ⚠️ Каждый чужой пролёт считается ОДИН РАЗ, даже если наш отрезок
; накрывает несколько его отрезков сразу (а он накрывает: у маршрута 2
; общий участок - один длинный кусок поверх нескольких коротких
; маршрута 1). Иначе один сосед насчитался бы за трёх, и провод уехал
; бы втрое дальше, чем надо.
;
; Аргументы:
;   P1, P2   - концы НАШЕГО отрезка;
;   SpanList - готовый список чужих пролётов (LEP:CollectExistingSpans).
;=====================================================================

;; ⚠️ Verts ОБЯЗАТЕЛЬНО в списке локальных, хотя это переменная foreach.
;; В AutoLISP область видимости динамическая: необъявленная переменная
;; foreach затёрла бы Verts вызывающей стороны - а в C:LEP-SPAN под этим
;; именем лежит список вершин МАРШРУТА, из которого дальше режется
;; пролёт. Тихая порча данных на ровном месте.
(defun LEP:CountOverlappingSpans (P1 P2 SpanList / Mid AngNew AngTolRad Count Hit i A B Proj AngOld Diff Verts)

    (setq Count 0)
    (setq AngTolRad (* pi (/ *LEP-Span-Overlap-AngleTol* 180.0)))

    (setq Mid
        (list
            (/ (+ (car P1) (car P2)) 2.0)
            (/ (+ (cadr P1) (cadr P2)) 2.0)
        )
    )
    (setq AngNew (angle P1 P2))

    (foreach Verts SpanList

        ;; Hit - "этот сосед уже засчитан". Обнуляется на каждого
        ;; соседа, поэтому один пролёт даёт максимум единицу.
        (setq Hit nil)
        (setq i 0)

        (while (and (not Hit) (< i (1- (length Verts))))

            (setq A (nth i Verts))
            (setq B (nth (1+ i) Verts))

            (if (> (distance A B) 1e-9)
                (progn
                    (setq Proj (LEP:ProjectPointOnSegment Mid A B))

                    (if (<= (distance Mid Proj) *LEP-Span-Overlap-Tolerance*)
                        (progn
                            (setq AngOld (angle A B))
                            (setq Diff (abs (- AngNew AngOld)))
                            (if (> Diff pi) (setq Diff (- (* 2.0 pi) Diff)))
                            (if (> Diff (/ pi 2.0)) (setq Diff (- pi Diff)))
                            (if (<= Diff AngTolRad) (setq Hit T))
                        )
                    )
                )
            )

            (setq i (1+ i))
        )

        (if Hit (setq Count (1+ Count)))
    )

    Count
)


;=====================================================================
; LEP:OffsetPointsPerSegment     (НОВАЯ 2026-08-06)
;
; Сдвигает вершины ломаной, где У КАЖДОГО ОТРЕЗКА СВОЙ сдвиг.
;
; Offsets - список сдвигов со знаком, по одному на отрезок, длиной
; ровно (число вершин - 1).
;
; ⚠️ ДВА ОТЛИЧИЯ ОТ СТАРОЙ LEP:OffsetPointList, и оба существенные:
;
; 1. НОРМАЛЬ СВОЯ У КАЖДОЙ ВЕРШИНЫ. Старая функция брала ОДИН
;    перпендикуляр - к прямой "первый конец пролёта - последний" - и
;    двигала по нему все точки разом. На прямом пролёте разницы нет.
;    Но пролёт маршрута 2 идёт своей улицей, потом сворачивает на
;    общий участок: общий перпендикуляр увёл бы линию вбок ПОД УГЛОМ
;    вместо параллельного сдвига, и она перестала бы быть параллельной
;    трассе на обоих кусках сразу.
;
; 2. СДВИГ РАЗНЫЙ НА РАЗНЫХ КУСКАХ. Отрезок без соседей остаётся на
;    месте (сдвиг 0), отрезок поверх чужого провода уезжает вбок.
;
; КАК СОБИРАЕТСЯ ПЕРЕХОД. Вершина берёт направление и сдвиг СВОЕГО
; отрезка (того, что из неё начинается), а последняя вершина - от
; последнего отрезка. Поэтому там, где сдвиг меняется, предыдущий
; отрезок сам становится чуть наклонным, и линия уходит вбок ПЛАВНО.
; Ступеньки не будет: чтобы её получить, пришлось бы специально
; вставлять лишнюю вершину. При сдвиге 0,3 м на отрезке в десятки
; метров отклонение меньше градуса - глазом не читается как излом.
;=====================================================================

(defun LEP:OffsetPointsPerSegment (Pts Offsets / N i Idx A B Dx Dy L Dist Result Pt)

    (setq N (length Pts))
    (setq i 0)
    (setq Result nil)

    (foreach Pt Pts

        ;; Индекс "своего" отрезка: у всех вершин - тот, что из неё
        ;; выходит; у самой последней своего нет, берём предыдущий.
        (setq Idx (if (< i (1- N)) i (- N 2)))

        (setq A (nth Idx Pts))
        (setq B (nth (1+ Idx) Pts))
        (setq Dist (nth Idx Offsets))

        (setq Dx (- (car B) (car A)))
        (setq Dy (- (cadr B) (cadr A)))
        (setq L (distance A B))

        (if (or (= Dist 0.0) (< L 1e-9))
            (setq Result (append Result (list Pt)))
            (setq Result
                (append Result
                    (list
                        (list
                            (+ (car  Pt) (* (/ (- Dy) L) Dist))
                            (+ (cadr Pt) (* (/    Dx  L) Dist))
                        )
                    )
                )
            )
        )

        (setq i (1+ i))
    )

    Result
)


;=====================================================================
; LEP:OffsetPointList
;
; ⚠️ БОЛЬШЕ НЕ ВЫЗЫВАЕТСЯ (2026-08-06). Заменена на
; LEP:OffsetPointsPerSegment выше - см. там, чем именно не устраивала.
; Оставлена на случай отката правки и как рабочий пример "сдвинуть всю
; ломаную как единое целое", если такое когда-нибудь понадобится.
;
; Сдвигает КАЖДУЮ точку списка Pts перпендикулярно направлению P1->P2
; на расстояние Dist (со знаком - в какую сторону, определяет знак).
;=====================================================================

(defun LEP:OffsetPointList (Pts P1 P2 Dist / Dx Dy Len Nx Ny Pt Result)
    (setq Result nil)
    (if (= Dist 0.0)
        Pts
        (progn
            (setq Dx (- (car P2) (car P1)))
            (setq Dy (- (cadr P2) (cadr P1)))
            (setq Len (distance P1 P2))
            (if (< Len 1e-9)
                Pts
                (progn
                    (setq Nx (/ (- Dy) Len))
                    (setq Ny (/ Dx Len))
                    (foreach Pt Pts
                        (setq Result
                            (append Result
                                (list (list (+ (car Pt) (* Nx Dist)) (+ (cadr Pt) (* Ny Dist))))
                            )
                        )
                    )
                    Result
                )
            )
        )
    )
)


;=====================================================================
; C:LEP-SPAN - основная команда
;
; Классификация одного или нескольких пролётов маршрута. Enter без
; точки (на первом клике пары) - выход из цикла.
;
; ✅ ФИКС 2026-07-22 (по просьбе пользователя): раньше команда СНАЧАЛА
; спрашивала клик по полилинии маршрута (и для этого клика нужно было
; не забыть включить LEP-ROUTEVIS, если слой скрыт) - хотя маршрут
; опоры и так уже известен из её собственной XDATA (ROUTE). Теперь
; трасса определяется САМА по ROUTE первой выбранной опоры
; (LEP:FindRouteByID) - отдельный клик по линии маршрута и, как
; следствие, необходимость включать LEP-ROUTEVIS перед запуском
; C:LEP-SPAN - больше не нужны (сам LEP-ROUTEVIS как команда никак не
; изменился, изменилось только то, что LEP-SPAN его больше не требует).
;
; ⚠️ НОВАЯ ПРОВЕРКА, которой не было даже у старой версии: если две
; выбранные опоры оказались на РАЗНЫХ трассах (ROUTE не совпадает) -
; переспрос "это Т-образное подключение веток?" (см. фикс v1.5), а не
; молчаливое создание пролёта непонятно к чему. Раньше явного клика по
; маршруту это не гарантировало вообще никак - код не проверял, что
; обе кликнутые опоры реально принадлежат выбранной трассе.
;
; ✅ ФИКС 2026-07-22 (v1.7, по просьбе пользователя) - ГЕОМЕТРИЧЕСКОЕ
; определение маршрута. Проблема, которую он описал: маршрут 2
; проложен ПОВЕРХ уже существующих опор маршрута 1 (общий участок, где
; висят два разных фидера, дальше расходятся) - опора в своей XDATA
; помнит ТОЛЬКО маршрут 1 (тот, которым её создали), и LEP-SPAN,
; механически копируя ROUTE с опоры, отнёс бы новые пролёты к маршруту
; 1, что бы пользователь ни имел в виду. Теперь маршрут определяется
; ГЕОМЕТРИЧЕСКИ (LEP:FindRoutesThroughPoints - какие полилинии реально
; проходят через ОБЕ кликнутые опоры):
;   1 кандидат  - берётся молча (обычный случай, поведение прежнее);
;   несколько   - ОДИН вопрос со списком, ответ ЗАПОМИНАЕТСЯ до конца
;                 сессии команды (следующие пролёты на неоднозначных
;                 парах опор идут туда же, без переспроса);
;   ноль        - откат на ROUTE опоры (как было).
; Геометрия пролёта и класс напряжения берутся у ВЫБРАННОГО маршрута,
; RouteID в XDATA пролёта - тоже его, поэтому вся остальная логика
; (ведомость, объединение подписей, LEP-SPAN-REPAIR) работает дальше
; сама, без единой правки.
;
; ⚠️ Опоры общего участка при этом ОСТАЮТСЯ за маршрутом 1 (их ROUTE
; никто не переписывает) - осознанное решение: на общем участке
; маршруту 2 нужен только ПРОВОД, сами опоры уже посчитаны в проекте 1
; (или существующие). Если когда-нибудь понадобится иначе - это
; отдельная задача, менять придётся XDATA самих опор.
;=====================================================================


;=====================================================================
;                    КОТЛОВАНЫ ГНБ (2026-08-11)
;=====================================================================
;
; ✅ ДОБАВЛЕНО 2026-08-11 по требованию пользователя: у любого
; ГНБ-прокола в реальности всегда есть рабочий котлован (там стоит
; буровая) и приёмный (там выходит бур). Раньше их рисовали руками на
; каждом чертеже.
;
; ⚠️ КОТЛОВАН - СВОЙСТВО УЗЛА (концевого блока), А НЕ ПРОЛЁТА. Это не
; деталь реализации, а то самое правило, из которого выходят ОБА
; требования пользователя разом (полное обоснование - в LEP-CONFIG.LSP,
; раздел "КОТЛОВАНЫ ГНБ"):
;   - несколько ПАРАЛЛЕЛЬНЫХ кабелей ГНБ висят на тех же концевых
;     блоках -> узел один -> котлован один;
;   - в точке смены направления (маркер TRANS) сходятся два прокола ->
;     узел опять один -> котлован один.
; Дедупликация - ПО ХЕНДЛУ УЗЛА (HOSTHANDLE), а не по расстоянию между
; точками: сравнение координат с допуском рано или поздно молча слепило
; бы два разных котлована или раздвоило один.
;
;=====================================================================


;=====================================================================
; LEP:PitExistsAtNode
;
; Есть ли на чертеже котлован, привязанный к узлу с хендлом NodeHandle.
; Ищет по слою *LEP-Layer-Pit* и сверяет ключ HOSTHANDLE в XDATA - это
; и есть та самая дедупликация "один узел = один котлован".
;
; ⚠️ Фильтр ssget "_X" не видит объекты на ЗАМОРОЖЕННЫХ слоях (на
; выключенных - видит). Слой котлованов печатаемый и морозить его
; незачем, но если пользователь всё же заморозит - в узле появится
; второй котлован поверх первого. Осознанный предел, как и у остальных
; сканов чертежа в этом файле.
;=====================================================================

(defun LEP:PitExistsAtNode (NodeHandle / SS i Ent Found)

    (setq Found nil)
    (setq SS (ssget "_X" (list (cons 0 "INSERT") (cons 8 *LEP-Layer-Pit*))))

    (if SS
        (progn
            (setq i 0)
            (while (and (< i (sslength SS)) (not Found))
                (setq Ent (ssname SS i))
                (if (= (LEP:GetDataValue Ent "HOSTHANDLE") NodeHandle)
                    (setq Found T)
                )
                (setq i (1+ i))
            )
        )
    )

    Found
)


;=====================================================================
; LEP:CreatePitLabel
;
; Выноска "Рабочий/Приемный котлован" (*LEP-Label-Pit*) на котлован с
; центром в точке Pt. Возвращает ename созданной выноски - её хендл
; уходит в XDATA котлована (LABELHANDLE), ровно как у подписи опоры и
; подписи пролёта.
;
; ⚠️ ОДНА ПОДПИСЬ НА ОБА ТИПА КОТЛОВАНА - решение пользователя
; 2026-08-11: программа не знает, с какой стороны прокола реально
; встанет буровая (это решает бурильщик на местности), а лишний вопрос
; при каждом проколе пользователь отвергнул. Лишнее слово стирается
; вручную при оформлении.
;
; ⚠️ "_.MLEADER" - КОМАНДА, значит рисует на ТЕКУЩЕМ слое. Поэтому
; CLAYER обязательно сохраняется, переключается на *LEP-Layer-Text* и
; возвращается в конце: ровно на этом уже терялись подписи КТП и киоска
; (уезжали на непечатаемый слой и не попадали в PDF).
;=====================================================================

(defun LEP:CreatePitLabel (Pt / OldLayer TextPt)

    (setq OldLayer (getvar "CLAYER"))
    (LEP:SetCurrentLayer *LEP-Layer-Text*)

    ;; Направление выноски - вверх-вправо, как у подписи пролёта (тот же
    ;; *LEP-LeaderOffset*). Единого "умного" направления тут быть не
    ;; может: рядом с котлованом стоит и опора со своей подписью, и
    ;; подпись самого пролёта, поэтому пользователь в любом случае
    ;; двигает выноски руками под конкретный чертёж.
    (setq TextPt
        (list
            (+ (car Pt) *LEP-LeaderOffset*)
            (+ (cadr Pt) *LEP-LeaderOffset*)
        )
    )

    (command "_.MLEADER" Pt TextPt *LEP-Label-Pit*)

    ;; Фон под текстом - свойство КАЖДОЙ выноски отдельно, не стиля
    ;; (см. LEP-CONFIG.LSP, раздел "ФОНОВАЯ МАСКА ТЕКСТА ВЫНОСОК").
    (LEP:SetMLeaderBackgroundMask (entlast))
    (LEP:BringToFront (entlast))

    (setvar "CLAYER" OldLayer)

    (entlast)
)


;=====================================================================
; LEP:PlacePitAtNode
;
; Ставит ОДИН котлован у конца прокола: узел NodeEnt (концевой блок -
; опора/КТП/киоск/маркер) с точкой вставки NodePt, геометрия прокола -
; Verts (⚠️ НЕСДВИНУТЫЙ SubVertsRaw, см. ниже), маршрут - RouteID.
;
; Если котлован в этом узле уже есть - НЕ ДЕЛАЕТ НИЧЕГО и возвращает
; nil. Именно здесь выполняются оба требования пользователя: и
; "параллельные кабели дают один котлован", и "в точке смены
; направления котлован один".
;
; КАК СЧИТАЕТСЯ ГЕОМЕТРИЯ:
;
; 1. ОРИЕНТАЦИЯ СПИСКА. Verts не обязан идти от P1 к P2: в C:LEP-SPAN
;    список вершин строится по индексам вершин маршрута и при Idx1 > Idx2
;    разворачивается. Поэтому "наш" конец определяется не по позиции в
;    списке, а по тому, к какой из двух крайних вершин ближе сам узел.
;
; 2. НАПРАВЛЕНИЕ - от узла ВНУТРЬ прокола, по первому же сегменту. Оно
;    же служит углом разворота блока: длинная сторона котлована ложится
;    вдоль оси прокола (в блоке она нарисована вдоль X, см.
;    LEP-PITSYM.LSP - поправки на 90° здесь нет и быть не должно).
;
; 3. ОТСТУП. Центр отходит от узла на *LEP-Pit-Offset* (1,5 м) внутрь -
;    чтобы котлован не накрыл символ опоры и не залез на границу чужого
;    участка. ⚠️ Отступ УЖИМАЕТСЯ, если прокол короткий:
;      - не больше 90% первого сегмента - иначе на проколе-"молнии"
;        (короткий отрезок, потом поворот) центр уехал бы ЗА излом, по
;        касательной в чистое поле;
;      - не больше трети всей длины прокола - иначе на проколе в пару
;        метров два котлована перепрыгнули бы друг друга и подпись
;        показывала бы на чужой конец.
;    Ужатие - с сообщением в консоль: молча смещать оформление нельзя,
;    иначе пользователь будет искать, почему котлован "не там".
;
; ⚠️ ГЕОМЕТРИЯ СЧИТАЕТСЯ ПО НЕСДВИНУТЫМ ВЕРШИНАМ (SubVertsRaw), а не по
; сдвинутой копии провода: параллельный сдвиг на 0,3 м - условность
; оформления, а котлован копают по НАСТОЯЩЕЙ оси прокола. То же правило,
; что уже действует для длин и размерных линий.
;
; Возвращает ename созданного котлована либо nil.
;=====================================================================

(defun LEP:PlacePitAtNode (NodeEnt NodePt Verts RouteID
                           / NodeHandle A B Ang SegLen TotalLen Off Center PitEnt LabelEnt)

    (setq NodeHandle (cdr (assoc 5 (entget NodeEnt))))

    (if (LEP:PitExistsAtNode NodeHandle)
        nil                                   ; котлован в этом узле уже стоит - выходим молча
        (progn

            ;; Наш конец списка - тот, к чьей крайней вершине узел ближе
            ;; (см. п.1 в шапке). B - соседняя вершина, направление
            ;; "внутрь прокола".
            (if (< (distance NodePt (car Verts)) (distance NodePt (last Verts)))
                (setq A (car Verts)
                      B (cadr Verts))
                (setq A (last Verts)
                      B (nth (- (length Verts) 2) Verts))
            )

            (setq Ang      (angle A B))
            (setq SegLen   (distance A B))
            (setq TotalLen (LEP:GetSpanLength Verts))

            (setq Off (min *LEP-Pit-Offset* (* 0.9 SegLen) (/ TotalLen 3.0)))

            (if (< Off *LEP-Pit-Offset*)
                (princ
                    (strcat
                        "\n[LEP-SPAN] Прокол короткий - отступ котлована ужат до "
                        (rtos Off 2 2) " м (обычно " (rtos *LEP-Pit-Offset* 2 2) " м)."
                    )
                )
            )

            (setq Center (polar A Ang Off))

            (setq PitEnt (LEP:InsertPitSymbol Center Ang))

            (setq LabelEnt (LEP:CreatePitLabel Center))

            ;; ⚠️ XDATA - ТОЛЬКО СТРОКИ (LEP:SetData собирает запись через
            ;; strcat). Числа здесь не появляются вообще: и RouteID, и оба
            ;; хендла - уже строки.
            ;; HOSTHANDLE - ключ дедупликации (см. LEP:PitExistsAtNode).
            ;; TYPE "PIT" в ведомость не попадает: LEP-REPORT.LSP ищет
            ;; свои слои и свои значения TYPE, этих там нет.
            (LEP:SetData
                PitEnt
                (list
                    (cons "TYPE" "PIT")
                    (cons "ROUTE" RouteID)
                    (cons "HOSTHANDLE" NodeHandle)
                    (cons "LABELHANDLE" (cdr (assoc 5 (entget LabelEnt))))
                )
            )

            PitEnt
        )
    )
)


;=====================================================================
; LEP:PlaceGnbPits
;
; Котлованы на ОБОИХ концах только что созданного ГНБ-прокола. Вся
; работа - в LEP:PlacePitAtNode (включая проверку "тут уже есть"), здесь
; только два вызова и счётчик для сообщения.
;
; ⚠️ Вызывается ТОЛЬКО при METHOD = "GNB". У траншеи котлованов нет: там
; копают всю трассу целиком, а не два приямка по концам.
;=====================================================================

(defun LEP:PlaceGnbPits (P1Ent P1Pt P2Ent P2Pt Verts RouteID / Made)

    (setq Made 0)

    (if (LEP:PlacePitAtNode P1Ent P1Pt Verts RouteID) (setq Made (1+ Made)))
    (if (LEP:PlacePitAtNode P2Ent P2Pt Verts RouteID) (setq Made (1+ Made)))

    (cond
        ((= Made 2) (princ "\n[LEP-SPAN] Поставлены котлованы ГНБ на обоих концах прокола."))
        ((= Made 1) (princ "\n[LEP-SPAN] Поставлен один котлован ГНБ - на втором конце он уже был."))
        (T          (princ "\n[LEP-SPAN] Котлованы ГНБ на обоих концах уже стояли - ничего не добавлено."))
    )

    Made
)


(defun C:LEP-SPAN (/ Route RouteID RouteID2 VClass Verts P1 P2 P1Pt P1Ent P2Pt P2Ent P1Handle P2Handle
                     Idx1 Idx2 SubVerts LineType WireList WireChoice MethodChoice Method
                     LayerName LtName SpanEnt SpanLength RealLength EndReserve DataList
                     Status OldOs OldError LEP-CatchResult TJunctionChoice IsCrossRoute VertexOk
                     SubVertsRaw ExistingSpans SegOffsets SegI NeedOffset D
                     RouteCandidates SessionRouteEnt)

    (setq OldError *error*)
    (defun *error* (msg)
        (if OldOs (setvar "OSMODE" OldOs))
        (setq *error* OldError)
        (princ (strcat "\nКоманда прервана: " msg))
        (princ)
    )

    (LEP:PrintHeader "Обработка пролётов и подписи")

    (setq OldOs (getvar "OSMODE"))
    (setvar "OSMODE" 0)

    (princ "\nДля каждого пролёта кликните ПО БЛОКУ первой опоры,")
    (princ "\nзатем ПО БЛОКУ второй опоры этого пролёта.")
    (princ "\nEnter вместо первой опоры - закончить.")

    (setq P1 (LEP:PickPole "\nПервая опора пролёта (Enter - закончить): "))

    (while P1

        (setq LEP-CatchResult
            (vl-catch-all-apply
                '(lambda ()

                    (setq P2 (LEP:PickPole "\nВторая опора пролёта: "))

                    (if P2
                        (progn
                            (setq P1Pt (car P1)) (setq P1Ent (cdr P1))
                            (setq P2Pt (car P2)) (setq P2Ent (cdr P2))
                            (setq P1Handle (cdr (assoc 5 (entget P1Ent))))
                            (setq P2Handle (cdr (assoc 5 (entget P2Ent))))

                            ;; Маршрут - по ROUTE первой опоры (см. ФИКС
                            ;; 2026-07-22 в шапке команды), со сверкой,
                            ;; что вторая опора с ней согласна.
                            (setq RouteID (LEP:GetDataValue P1Ent "ROUTE"))
                            (setq RouteID2 (LEP:GetDataValue P2Ent "ROUTE"))
                            (if (not RouteID) (setq RouteID "LEP_ROUTE_UNKNOWN"))
                            (if (not RouteID2) (setq RouteID2 "LEP_ROUTE_UNKNOWN"))

                            ;;=====================================================
                            ;; ШАГ 1. ГЕОМЕТРИЯ - КАКОЙ МАРШРУТ ФИЗИЧЕСКИ ПРОХОДИТ
                            ;;         ЧЕРЕЗ ОБЕ КЛИКНУТЫЕ ТОЧКИ
                            ;;
                            ;; ⚠️ ПОРЯДОК ПЕРЕСТРОЕН 2026-08-05 (баг найден
                            ;; пользователем на живом чертеже). РАНЬШЕ первым шёл
                            ;; вопрос "это Т-образное подключение?", и геометрия
                            ;; спрашивалась ТОЛЬКО если пользователь ответил "Нет".
                            ;; Из-за этого целый нормальный сценарий был недоступен
                            ;; ВООБЩЕ, ни одним ответом:
                            ;;
                            ;;   Маршрут 2 идёт своей улицей, потом ВЛИВАЕТСЯ в
                            ;;   маршрут 1 и дальше идёт с ним по общим опорам до
                            ;;   той же ТП. Пользователь кликает первую опору
                            ;;   маршрута 2 и ТП.
                            ;;
                            ;; Первая опора числится за маршрутом 2, ТП - за
                            ;; маршрутом 1 (её ставили с ним), XDATA разная - и
                            ;; вылезал вопрос про Т-образное:
                            ;;   ответ "Да"  -> IsCrossRoute -> Verts = ДВЕ ТОЧКИ ->
                            ;;                  пролёт рисуется ПРЯМОЙ ЛИНИЕЙ через
                            ;;                  всё поле, мимо маршрута;
                            ;;   ответ "Нет" -> команда отказывалась работать вовсе.
                            ;; При этом маршрут 2 физически проходит через ОБЕ точки,
                            ;; и геометрия ответила бы правильно - но её не спрашивали.
                            ;;
                            ;; Логика была перевёрнута: XDATA (кем опору СОЗДАЛИ,
                            ;; записано навсегда) решала раньше, чем геометрия (как
                            ;; трасса лежит на чертеже СЕЙЧАС). Теперь наоборот -
                            ;; сначала смотрим на чертёж, и только если на чертеже
                            ;; такой трассы нет, спрашиваем про Т-образное.
                            ;;
                            ;; Сам поиск (LEP:FindRoutesThroughPoints, добавлен
                            ;; 2026-07-22) не изменился:
                            ;;   1 кандидат  - берём молча, ноль вопросов;
                            ;;   несколько   - ОДИН вопрос, ответ запоминается до
                            ;;                 конца сессии команды (SessionRouteEnt);
                            ;;   ноль        - идём к шагу 2.
                            ;;=====================================================
                            (setq Route nil)
                            (setq RouteCandidates (LEP:FindRoutesThroughPoints P1Pt P2Pt))

                            (cond
                                ((= (length RouteCandidates) 1)
                                 (setq Route (car RouteCandidates))
                                )
                                ((> (length RouteCandidates) 1)
                                 ;; Запомненный на эту сессию выбор - если он всё ещё
                                 ;; среди кандидатов для ЭТОЙ пары опор.
                                 (if (and SessionRouteEnt (member SessionRouteEnt RouteCandidates))
                                     (setq Route SessionRouteEnt)
                                     (progn
                                         (setq Route (LEP:ChooseRouteFromCandidates RouteCandidates))
                                         (if Route (setq SessionRouteEnt Route))
                                     )
                                 )
                                )
                            )

                            ;;=====================================================
                            ;; ШАГ 2. Т-ОБРАЗНОЕ ПОДКЛЮЧЕНИЕ - ТОЛЬКО ЕСЛИ ГЕОМЕТРИЯ
                            ;;         НИЧЕГО НЕ НАШЛА
                            ;;
                            ;; Настоящее Т-образное подключение - это когда опора
                            ;; трассы 2 цепляется к опоре трассы 1, и МАРШРУТА,
                            ;; ПРОХОДЯЩЕГО ЧЕРЕЗ ОБЕ, на чертеже действительно нет.
                            ;; Тогда прямая линия P1-P2 - верная геометрия.
                            ;; Если же такой маршрут нашёлся - вопрос не нужен: это
                            ;; не подключение вбок, а обычный пролёт вдоль трассы.
                            ;;=====================================================
                            (cond

                                ;; Геометрия нашла маршрут - идём по нему.
                                (Route
                                    (setq IsCrossRoute nil)
                                    ;; Сообщаем, только если XDATA опор разошлась -
                                    ;; иначе это обычный случай, и молчать правильно.
                                    (if (/= RouteID RouteID2)
                                        (princ "\n[LEP-SPAN] Опоры числятся за разными трассами, но через обе физически проходит маршрут - пролёт пойдёт ПО НЕМУ, а не по прямой.")
                                    )
                                )

                                ;; Геометрии нечего сказать, а трассы разные - вот
                                ;; теперь спрашиваем.
                                ((/= RouteID RouteID2)
                                    ;; ⚠️ ФИКС 2026-08-05 (найдено пользователем на живом
                                    ;; чертеже, при построении второго маршрута поверх
                                    ;; первого). Префикс "[LEP-SPAN]" печатается ОТДЕЛЬНЫМ
                                    ;; princ, а НЕ внутри строки getkword - и это не
                                    ;; косметика.
                                    ;;
                                    ;; Dynamic Input (подсказка у курсора) строит выпадающий
                                    ;; список вариантов ответа из ПЕРВОЙ группы в квадратных
                                    ;; скобках, которую найдёт в тексте запроса - какой бы
                                    ;; эта группа ни была. Наш собственный префикс стоял
                                    ;; первым, поэтому в списке у курсора оказывался пункт
                                    ;; "LEP-SPAN" вместо "Да"/"Нет". В КОНСОЛИ при этом всё
                                    ;; выглядело правильно (там текст просто печатается как
                                    ;; есть), поэтому баг и прожил незамеченным.
                                    ;;
                                    ;; ⚠️ ПРАВИЛО НА БУДУЩЕЕ: в строке запроса к getkword/
                                    ;; getreal/getpoint единственная группа в квадратных
                                    ;; скобках должна быть СПИСКОМ ОТВЕТОВ. Всё остальное -
                                    ;; префиксы, пояснения - либо отдельным princ, либо без
                                    ;; скобок. Остальные запросы проекта (LEP:GetStatus в
                                    ;; LEP-UTILS.LSP, выбор эталона в LEP-SCALE.LSP) этому
                                    ;; правилу и так соответствуют - проверено при поиске.
                                    ;;
                                    ;; ⚠️ princ стоит ПЕРЕД initget, а не между initget и
                                    ;; getkword: initget действует на СЛЕДУЮЩИЙ запрос, и
                                    ;; ставить между ними что-либо - лишний риск на ровном
                                    ;; месте.
                                    (princ "\n[LEP-SPAN] Опоры на РАЗНЫХ трассах.")
                                    (initget "Да Нет")
                                    (setq TJunctionChoice
                                        (getkword "\nЭто Т-образное подключение веток (не ошибка)? [Да/Нет] <Нет>: ")
                                    )
                                    (setq IsCrossRoute (= TJunctionChoice "Да"))
                                )

                                ;; Трассы одинаковые, геометрия молчит (полилинию
                                ;; могли подвинуть) - обычная работа, откат ниже.
                                (t (setq IsCrossRoute nil))
                            )

                            ;;=====================================================
                            ;; ШАГ 3. ОТКАЗ - только когда идти реально некуда
                            ;;
                            ;; ⚠️ В условие добавлено (not Route) 2026-08-05: без
                            ;; него команда отказывалась бы работать ровно в том
                            ;; случае, который эта правка и чинит - геометрия нашла
                            ;; маршрут, а XDATA опор при этом разная.
                            ;;=====================================================
                            (if (and (not Route) (/= RouteID RouteID2) (not IsCrossRoute))
                                (princ "\n[LEP-SPAN] Отменено - кликните обе опоры одного маршрута, либо подтвердите Т-образное подключение.")
                                (progn
                                    ;; Откат на старое поведение - маршрут по ROUTE первой
                                    ;; опоры. Сюда попадаем в двух случаях: настоящее
                                    ;; Т-образное подключение (маршрута через обе точки нет
                                    ;; и не должно быть) либо геометрия ничего не нашла
                                    ;; (например, полилинию маршрута двигали руками).
                                    (if (not Route)
                                        (setq Route (LEP:FindRouteByID RouteID))
                                    )

                                    (if (not Route)
                                        (princ (strcat "\n[LEP-SPAN] Не найдена полилиния трассы " RouteID " на чертеже - пропускаю."))
                                        (progn
                                    ;; RouteID - ПЕРЕОПРЕДЕЛЯЕМ по РЕАЛЬНО выбранному маршруту
                                    ;; (он мог оказаться не тем, что записан в XDATA опоры -
                                    ;; см. геометрическое определение выше). Именно этот ID
                                    ;; уйдёт в XDATA пролёта, а значит и в ведомость, и в
                                    ;; объединение подписей - вся остальная логика ниже
                                    ;; работает без изменений.
                                    (setq RouteID (LEP:GetDataValue Route "ID"))
                                    (if (not RouteID) (setq RouteID "LEP_ROUTE_UNKNOWN"))

                                    ;; Класс напряжения - у ВЫБРАННОГО маршрута (не у маршрута
                                    ;; опоры): список марок провода должен соответствовать
                                    ;; тому фидеру, который сейчас чертим.
                                    (setq VClass (LEP:GetDataValue Route "VCLASS"))

                                    ;; ⚠️ Т-образное подключение (IsCrossRoute) - опоры на
                                    ;; РАЗНЫХ полилиниях, нет ЕДИНОЙ трассы, из вершин которой
                                    ;; можно вырезать SubVerts. Подставляем "трассу из двух
                                    ;; точек" (P1Pt, P2Pt) - вся нарезка ниже (Idx1/Idx2/
                                    ;; SubList) на такой Verts естественно даёт SubVerts = сама
                                    ;; прямая P1Pt-P2Pt, без отдельной ветки кода ниже.
                                    ;;
                                    ;; ✅ ДОБАВЛЕНО 2026-08-05: перед тем как читать вершины,
                                    ;; УБЕЖДАЕМСЯ, что вершины вообще есть В ТОЧКАХ КЛИКА
                                    ;; (LEP:EnsureVertexAtPoint - подробная шапка у функции).
                                    ;; Без этой проверки нарезка ниже молча привязывалась к
                                    ;; ближайшей вершине, КАКОЙ БЫ ДАЛЁКОЙ ОНА НИ БЫЛА:
                                    ;; LEP:GetNearestVertexIndex расстояние не проверяет вообще.
                                    ;; Ловится это на реальном сценарии "маршрут 2 вливается в
                                    ;; маршрут 1 у той же ТП": опоры общего участка принадлежат
                                    ;; маршруту 1, и вершин маршрута 2 в них нет.
                                    ;; ⚠️ ПОРЯДОК ВАЖЕН: функция МОЖЕТ вставить вершину, поэтому
                                    ;; LEP:GetVertices вызывается ПОСЛЕ неё, а не до.
                                    ;; ⚠️ При Т-образном подключении проверка не нужна и не
                                    ;; применяется: там "вершины" - это сами кликнутые точки.
                                    (if IsCrossRoute
                                        (progn
                                            (setq VertexOk T)
                                            (setq Verts (list P1Pt P2Pt))
                                        )
                                        (progn
                                            ;; Обе точки проверяем ПО ОТДЕЛЬНОЙ строке, а не
                                            ;; через (and ...): у and вторая проверка не
                                            ;; выполнилась бы, если первая вернула nil - а нам
                                            ;; надо, чтобы пользователь увидел в консоли ОБЕ
                                            ;; проблемы сразу, а не чинил их по одной.
                                            (setq VertexOk (LEP:EnsureVertexAtPoint Route P1Pt))
                                            (if (not (LEP:EnsureVertexAtPoint Route P2Pt))
                                                (setq VertexOk nil)
                                            )
                                            (setq Verts (LEP:GetVertices Route))
                                        )
                                    )

                                    ;; Находим ближайшие вершины маршрута к P1Pt и P2Pt
                                    (setq Idx1 (LEP:GetNearestVertexIndex Verts P1Pt))
                                    (setq Idx2 (LEP:GetNearestVertexIndex Verts P2Pt))

                                    ;; Берём подсписок вершин между ними (по возрастанию индекса)
                                    (if (> Idx1 Idx2)
                                        (progn (setq Idx1 (LEP:GetNearestVertexIndex Verts P2Pt))
                                               (setq Idx2 (LEP:GetNearestVertexIndex Verts P1Pt)))
                                    )
                                    (setq SubVerts
                                        (LEP:SubList Verts Idx1 Idx2)
                                    )

                                    ;; ПАРАЛЛЕЛЬНЫЙ СДВИГ - ПОСЕГМЕНТНО
                                    ;;
                                    ;; ✅ ДОБАВЛЕНО 2026-07-22: если по этому месту уже идёт
                                    ;; провод, без сдвига новая линия легла бы ТОЧНО поверх
                                    ;; старой, подписи - друг на друге.
                                    ;;
                                    ;; ⚠️ ПЕРЕПИСАНО 2026-08-06. Раньше считалось совпадение
                                    ;; ПАРЫ ХЕНДЛОВ ОПОР (LEP:FindSamePolePairSpans) и один
                                    ;; сдвиг применялся ко ВСЕМУ пролёту. У двух маршрутов,
                                    ;; совпадающих ЧАСТИЧНО (маршрут 2 вливается в маршрут 1
                                    ;; и идёт с ним до общей ТП), пары концов РАЗНЫЕ -
                                    ;; совпадение не находилось, сдвиг не срабатывал, провода
                                    ;; ложились друг на друга. Теперь перекрытие ищется
                                    ;; ГЕОМЕТРИЧЕСКИ и ОТДЕЛЬНО ДЛЯ КАЖДОГО ОТРЕЗКА: своя
                                    ;; улица маршрута 2 остаётся на месте, общий с маршрутом 1
                                    ;; участок уезжает вбок. Подробности - в шапках
                                    ;; LEP:CountOverlappingSpans и LEP:OffsetPointsPerSegment.
                                    ;;
                                    ;; ⚠️ SubVertsRaw - НЕСДВИНУТАЯ геометрия, она нужна дальше
                                    ;; для размерных линий. Размеры должны стоять по НАСТОЯЩЕЙ
                                    ;; трассе, а не по сдвинутой на 0,3 м копии провода: сдвиг
                                    ;; это условность оформления, а размер - реальное
                                    ;; расстояние между опорами. Раньше этот инвариант держался
                                    ;; сам собой (сдвиг применялся только при ParallelN > 0, а
                                    ;; размеры рисовались только при ParallelN = 0) - с
                                    ;; посегментным сдвигом так больше не выходит, и раздельные
                                    ;; списки стали обязательны.
                                    (setq SubVertsRaw SubVerts)
                                    (setq ExistingSpans (LEP:CollectExistingSpans))
                                    (setq SegOffsets nil)
                                    (setq SegI 0)
                                    (while (< SegI (1- (length SubVerts)))
                                        (setq SegOffsets
                                            (append SegOffsets
                                                (list
                                                    (LEP:GetParallelOffset
                                                        (LEP:CountOverlappingSpans
                                                            (nth SegI SubVerts)
                                                            (nth (1+ SegI) SubVerts)
                                                            ExistingSpans
                                                        )
                                                    )
                                                )
                                            )
                                        )
                                        (setq SegI (1+ SegI))
                                    )
                                    ;; Обычным foreach, а не через apply/mapcar: в AutoLISP
                                    ;; (apply 'or ...) ведёт себя не так очевидно, как в
                                    ;; обычном Lisp, а проверить это вживую сейчас негде -
                                    ;; см. правило проекта про непроверенный синтаксис.
                                    (setq NeedOffset nil)
                                    (foreach D SegOffsets
                                        (if (/= D 0.0) (setq NeedOffset T))
                                    )
                                    (if NeedOffset
                                        (setq SubVerts (LEP:OffsetPointsPerSegment SubVerts SegOffsets))
                                    )

                                    ;; ✅ 2026-08-05: к прежней точке отказа ("между точками нет
                                    ;; отдельного участка маршрута") добавлен отказ по проверке
                                    ;; вершин. Оба отказа объединены в ОДНО условие СОЗНАТЕЛЬНО,
                                    ;; а не сделаны отдельными вложенными if: остаток команды -
                                    ;; несколько сотен строк на глубине в десяток вложений, и
                                    ;; лишний уровень отступа ради одной проверки сделал бы их
                                    ;; совсем нечитаемыми.
                                    ;; ⚠️ Сообщения РАЗНЫЕ, и это важно: причины разные, а
                                    ;; печатать "нет отдельного участка маршрута" там, где на
                                    ;; самом деле опора оказалась не на той трассе, значит
                                    ;; отправить пользователя искать несуществующую проблему.
                                    ;; В случае с вершинами подробную причину уже напечатала
                                    ;; LEP:EnsureVertexAtPoint, здесь только отсылка к ней.
                                    (if (or (not VertexOk) (< (length SubVerts) 2))
                                        (if VertexOk
                                            (princ "\n[LEP-SPAN] Между этими точками нет отдельного участка маршрута - пропускаю.")
                                            (princ "\n[LEP-SPAN] Пролёт не построен - причина в сообщении выше.")
                                        )
                                        (progn
                                            ;; Тип прокладки
                                            (setq LineType
                                                (LEP:ChooseFromList
                                                    (list (cons "ВЛ (воздух)" "VL") (cons "КЛ (земля)" "KL"))
                                                    "Тип прокладки"
                                                )
                                            )

                                            (if LineType
                                                (progn
                                                    ;; Статус - ПЕРЕД выбором слоя/способа прокладки КЛ
                                                    ;; (⚠️ ФИКС 2026-07-22: раньше спрашивался ПОСЛЕ марки -
                                                    ;; переставлено, т.к. выбор ГНБ/Траншея ниже нужен ТОЛЬКО
                                                    ;; для Проект. КЛ, значит статус должен быть уже известен).
                                                    (setq Status (LEP:GetStatus "пролёта"))

                                                    (if (= (cdr LineType) "VL")
                                                        (progn
                                                            ;; СИП-3 - для 10кВ и 6кВ (магистраль, разные
                                                            ;; списки марок - см. *LEP-WireTypes-VL-6* в
                                                            ;; CONFIG), СИП-2 - только для 0,4кВ (низкое
                                                            ;; напряжение) - список марок выбирается по
                                                            ;; классу МАРШРУТА, а не общий на все случаи.
                                                            ;; ⚠️ ФИКС 2026-07-22: раньше был бинарный (if
                                                            ;; VClass="10" ... иначе 04) - "6" молча попадал
                                                            ;; бы в ветку 0,4кВ (СИП-2) как "любой не 10" -
                                                            ;; теперь три явные ветки.
                                                            (cond
                                                                ((= VClass "10") (setq WireList *LEP-WireTypes-VL-10*))
                                                                ((= VClass "6")  (setq WireList *LEP-WireTypes-VL-6*))
                                                                (t               (setq WireList *LEP-WireTypes-VL-04*))
                                                            )
                                                            ;; ✅ ДОБАВЛЕНО 2026-07-22: слой ВЛ теперь по
                                                            ;; классу напряжения x статус (4 granular слоя,
                                                            ;; см. LEP-CONFIG.LSP) - *LEP-Layer-Proj-VL*/
                                                            ;; *LEP-Layer-Exist-VL* САМИ ПО СЕБЕ больше НЕ
                                                            ;; годятся для вставки (это составная строка
                                                            ;; "слой1,слой2" для сканирования, см. CONFIG).
                                                            (if (= Status "PROJECT")
                                                                (if (= VClass "04")
                                                                    (setq LayerName *LEP-Layer-Proj-VL-04*)
                                                                    (setq LayerName *LEP-Layer-Proj-VL-10*)
                                                                )
                                                                (if (= VClass "04")
                                                                    (setq LayerName *LEP-Layer-Exist-VL-04*)
                                                                    (setq LayerName *LEP-Layer-Exist-VL-10*)
                                                                )
                                                            )
                                                            (setq LtName "CONTINUOUS")
                                                            (setq Method nil)
                                                        )
                                                        (progn
                                                            ;; КЛ рисуется ТАК ЖЕ, как ВЛ - сплошной линией,
                                                            ;; никакого своего типа линии со штампом "K"
                                                            ;; больше нет (убрано по просьбе пользователя
                                                            ;; 2026-07-15 - см. LEP-README.md). Отличие КЛ
                                                            ;; от ВЛ на чертеже - слой/цвет.
                                                            (setq WireList *LEP-WireTypes-KL*)
                                                            (setq LtName "CONTINUOUS")

                                                            ;; ✅ ДОБАВЛЕНО 2026-07-22 (по просьбе пользователя):
                                                            ;; способ прокладки (ГНБ/Траншея) - ТОЛЬКО для
                                                            ;; Проект. КЛ (Сущ. КЛ уже проложена каким-то
                                                            ;; способом де-факто, спрашивать не о чем - остаётся
                                                            ;; на старом едином слое существующих КЛ).
                                                            (if (= Status "PROJECT")
                                                                (progn
                                                                    (setq MethodChoice
                                                                        (LEP:ChooseFromList
                                                                            (list (cons "ГНБ" "GNB") (cons "Траншея" "TRENCH"))
                                                                            "Способ прокладки КЛ"
                                                                        )
                                                                    )
                                                                    (setq Method (if MethodChoice (cdr MethodChoice) "TRENCH"))
                                                                    (setq LayerName
                                                                        (if (= Method "GNB")
                                                                            *LEP-Layer-Proj-KL-GNB*
                                                                            *LEP-Layer-Proj-KL-Trench*
                                                                        )
                                                                    )
                                                                )
                                                                (progn
                                                                    (setq Method nil)
                                                                    (setq LayerName *LEP-Layer-Exist-KL*)
                                                                )
                                                            )
                                                        )
                                                    )

                                                    ;; Марка провода/кабеля - список из CONFIG
                                                    (setq WireChoice (LEP:ChooseFromList WireList "Марка провода/кабеля"))

                                                    (if WireChoice
                                                        (progn
                                                            (setq SpanEnt (LEP:CreateSpanEntity SubVerts LayerName LtName))

                                                            ;; ✅ ДОБАВЛЕНО 2026-07-22 (по прямому замечанию
                                                            ;; пользователя): толщина линии по статусу (Проект.
                                                            ;; жирнее Сущ.) - раньше была только у символа опоры
                                                            ;; (LEP:InsertPoleSymbol, LEP-POLESYM.LSP), у пролётов
                                                            ;; группа DXF 370 не выставлялась вообще - все пролёты
                                                            ;; были одинаковой (дефолтной) толщины независимо от
                                                            ;; статуса. Переиспользует ту же общую функцию и те же
                                                            ;; константы (*LEP-LWeight-Proj*/*LEP-LWeight-Exist*),
                                                            ;; что и у опор - для единообразия чертежа.
                                                            (if (= Status "EXIST")
                                                                (LEP:SetEntityLWeight SpanEnt *LEP-LWeight-Exist*)
                                                                (LEP:SetEntityLWeight SpanEnt *LEP-LWeight-Proj*)
                                                            )

                                                            ;; SpanLength - геометрический путь вдоль трассы (может
                                                            ;; не совпадать с прямым расстоянием P1-P2, если между
                                                            ;; опорами есть изгиб без опоры) - "сырая" длина БЕЗ
                                                            ;; запаса, основа и для RealLength (ведомость), и для
                                                            ;; подписи ВЛ без запаса (LEP:FinalizeSpanLabel).
                                                            ;; ⚠️ 2026-08-05: рядом тут же считалась DimDistance -
                                                            ;; ПРЯМОЕ расстояние P1Pt-P2Pt для размерной линии ВЛ.
                                                            ;; Переменная УДАЛЕНА вместе с веткой "у ВЛ один размер
                                                            ;; на пролёт": теперь размеры и у ВЛ, и у КЛ рисует
                                                            ;; LEP:CreateSpanDimensions, а она меряет участки сама
                                                            ;; по SubVerts. Готовое число ей не передаётся, и
                                                            ;; считать его тут стало незачем - см. подробное
                                                            ;; обоснование ниже, у самого вызова.
                                                            ;; ⚠️ 2026-07-24: у LEP:GetRealLength теперь ЧЕТЫРЕ
                                                            ;; аргумента - к типу линии добавились способ
                                                            ;; прокладки (свой процент запаса у ГНБ и траншеи)
                                                            ;; и класс напряжения (10/6 кВ - три фазы, три
                                                            ;; отдельных провода на пролёт). См. подробную
                                                            ;; шапку функции выше в этом файле.
                                                            ;; ⚠️ 2026-07-24: метры на концевые заделки КЛ
                                                            ;; считаются ПОКОНЦОВО, по типу того, что на
                                                            ;; конце стоит (опора - 3 м на подъём, наземные
                                                            ;; КТП/киоск - сейчас 0 м). Считаем ЗДЕСЬ, где
                                                            ;; ещё есть сами объекты концов, и сохраняем
                                                            ;; готовое число в XDATA - потом, при пересчёте
                                                            ;; общей подписи группы, объектов под рукой уже
                                                            ;; нет, а складывать запасы разных пролётов надо.
                                                            ;; ⚠️ 2026-08-06: длина считается по SubVertsRaw
                                                            ;; (НЕсдвинутой геометрии), а не по SubVerts.
                                                            ;; Пока сдвиг был одинаковым на весь пролёт, разницы
                                                            ;; не было вообще: параллельный перенос не меняет
                                                            ;; длин отрезков. С посегментным сдвигом отрезок, на
                                                            ;; котором сдвиг МЕНЯЕТСЯ, становится чуть наклонным
                                                            ;; и чуть длиннее - а в ведомость должна идти длина
                                                            ;; по настоящей трассе, а не по оформительской копии.
                                                            (setq SpanLength (LEP:GetSpanLength SubVertsRaw))
                                                            (setq EndReserve (LEP:GetEndReserve P1Ent P2Ent))
                                                            (setq RealLength (LEP:GetRealLength (cdr LineType) Method VClass SpanLength EndReserve))

                                                            ;; Данные для ведомости: трасса, статус, марка, сечение,
                                                            ;; РЕАЛЬНАЯ длина с запасом (LENGTH, не сырое расстояние) -
                                                            ;; ведомость всегда с запасом, независимо от того, что
                                                            ;; показывает подпись на чертеже (см. RAWLENGTH/
                                                            ;; LEP:FinalizeSpanLabel - только ВЛ на чертеже теряет
                                                            ;; запас, ведомость - никогда). POLE1HANDLE/POLE2HANDLE -
                                                            ;; для поиска соседних пролётов при объединении подписей.
                                                            (setq DataList
                                                                (list
                                                                    (cons "TYPE" "SPAN")
                                                                    (cons "ROUTE" RouteID)
                                                                    (cons "STATUS" Status)
                                                                    (cons "WIRE" (car WireChoice))
                                                                    (cons "SECTION" (cdr WireChoice))
                                                                    (cons "LENGTH" (itoa RealLength))
                                                                    (cons "RAWLENGTH" (rtos SpanLength 2 3))
                                                                    (cons "RESERVE" (rtos EndReserve 2 3))
                                                                    (cons "POLE1HANDLE" P1Handle)
                                                                    (cons "POLE2HANDLE" P2Handle)
                                                                )
                                                            )
                                                            (if Method
                                                                (setq DataList (append DataList (list (cons "METHOD" Method))))
                                                            )
                                                            (LEP:SetData SpanEnt DataList)

                                                            ;; Подпись - объединяется с соседними пролётами той же
                                                            ;; марки/статуса автоматически (LEP:FinalizeSpanLabel,
                                                            ;; см. её подробную шапку выше в этом файле).
                                                            (LEP:FinalizeSpanLabel SpanEnt Verts P1Handle P2Handle (cdr LineType) (car WireChoice) Status)

                                                            ;; Размерная линия показывает ГЕОМЕТРИЮ, которая ОДНА
                                                            ;; И ТА ЖЕ для всех параллельных проводов на этом
                                                            ;; месте - рисовать её каждому проводу заново было бы
                                                            ;; чистым мусором.
                                                            ;; ⚠️ 2026-08-04: у КЛ размер рисуется НА КАЖДОЕ
                                                            ;; КОЛЕНО (LEP:CreateSpanDimensions, мн. ч.) -
                                                            ;; кабельная траншея часто идёт "молнией", и одна
                                                            ;; линия "по прямой от конца до конца" показывала бы
                                                            ;; меньше, чем реально копают.
                                                            ;;
                                                            ;; ✅ 2026-08-05: ТЕПЕРЬ ТАК ЖЕ И У ВЛ. Раньше здесь
                                                            ;; было ветвление "КЛ - по коленам, ВЛ - одна линия
                                                            ;; по прямой P1Pt-P2Pt"; ветку ВЛ отложили 04.08 не
                                                            ;; потому, что она чем-то плоха, а потому, что её не
                                                            ;; успели проверить вживую.
                                                            ;;
                                                            ;; ЗАЧЕМ УБРАЛ ВЕТВЛЕНИЕ (просьба пользователя):
                                                            ;; на длинной прямой ВЛ из десятка опор приходилось
                                                            ;; обкликивать КАЖДУЮ пару опор - хотя данные (марка,
                                                            ;; статус, класс) на всём участке одни и те же, и
                                                            ;; единственное, ради чего нужны отдельные пролёты, -
                                                            ;; это как раз размерные линии между соседними
                                                            ;; опорами. Посегментные размеры снимают эту нужду:
                                                            ;; можно кликнуть ПЕРВУЮ и ПОСЛЕДНЮЮ опору, а размер
                                                            ;; всё равно появится на каждом участке между
                                                            ;; вершинами, то есть между каждой парой опор
                                                            ;; (у каждой опоры своя вершина - её вставляет
                                                            ;; LEP:InsertVertexOnRoute, и символ опоры стоит
                                                            ;; РОВНО в этой вершине, см. LEP:PlacePoleOnRoute).
                                                            ;;
                                                            ;; ПОЧЕМУ ЭТО БЕЗОПАСНО ДЛЯ ОБЫЧНОГО ПОКЛИКОВОГО
                                                            ;; СЦЕНАРИЯ: у пролёта между двумя СОСЕДНИМИ опорами
                                                            ;; SubVerts - это ровно две точки, значит один
                                                            ;; участок и один размер, как и раньше. И точки эти
                                                            ;; те же самые: символ опоры вставлен в вершину, то
                                                            ;; есть P1Pt совпадает с первой точкой SubVerts.
                                                            ;;
                                                            ;; ГДЕ РАЗНИЦА ВСЁ-ТАКИ БУДЕТ: если трасса гнётся
                                                            ;; МЕЖДУ опорами (излом без опоры), раньше ВЛ
                                                            ;; рисовала один размер по прямой - то есть меньше,
                                                            ;; чем провод реально проходит. Теперь будет два
                                                            ;; размера по коленам. Это исправление, а не регресс.
                                                            ;;
                                                            ;; ⚠️ ПЕРЕПИСАНО 2026-08-06, ДВА ИЗМЕНЕНИЯ.
                                                            ;;
                                                            ;; 1. УБРАНО УСЛОВИЕ (= ParallelN 0). Оно было
                                                            ;;    единственной защитой от дублей размеров до
                                                            ;;    05.08 и означало "второй провод на этой паре
                                                            ;;    опор размеров не рисует вообще". С посегментным
                                                            ;;    сдвигом это условие стало ВРЕДНЫМ: у пролёта
                                                            ;;    маршрута 2 перекрыт только хвост, но одного
                                                            ;;    перекрытого отрезка хватило бы, чтобы выключить
                                                            ;;    размеры НА ВСЁМ пролёте - включая его
                                                            ;;    собственную улицу, где никаких дублей нет.
                                                            ;;    Теперь решает LEP:DimensionAlreadyThere -
                                                            ;;    ОТДЕЛЬНО ПО КАЖДОМУ УЧАСТКУ, "есть ли уже
                                                            ;;    размерная линия на этом месте". Она и так
                                                            ;;    гасит повтор на паре опор, ради которого
                                                            ;;    условие ставилось.
                                                            ;;
                                                            ;; 2. ПЕРЕДАЁМ SubVertsRaw, А НЕ SubVerts. Размер
                                                            ;;    должен стоять по НАСТОЯЩЕЙ трассе, а не по
                                                            ;;    сдвинутой на 0,3 м копии провода: сдвиг - это
                                                            ;;    условность оформления, а размер - реальное
                                                            ;;    расстояние между опорами. Раньше инвариант
                                                            ;;    держался сам собой (сдвиг и размеры не могли
                                                            ;;    случиться одновременно), теперь его надо
                                                            ;;    соблюдать явно.
                                                            (LEP:CreateSpanDimensions SubVertsRaw)

                                                            ;; ✅ ДОБАВЛЕНО 2026-08-11: КОТЛОВАНЫ ГНБ на обоих
                                                            ;; концах прокола (рабочий и приёмный). Только для
                                                            ;; ГНБ - у траншеи котлованов нет, там копают всю
                                                            ;; трассу целиком.
                                                            ;;
                                                            ;; ⚠️ Ставится по УЗЛАМ, а не по пролётам, поэтому
                                                            ;; второй параллельный кабель и второй прокол через
                                                            ;; маркер смены направления НИЧЕГО НЕ ДОБАВЯТ -
                                                            ;; проверка "в этом узле котлован уже есть" сидит
                                                            ;; внутри LEP:PlacePitAtNode. Полное обоснование - в
                                                            ;; шапке раздела "КОТЛОВАНЫ ГНБ" выше в этом файле.
                                                            ;;
                                                            ;; ⚠️ SubVertsRaw, а не SubVerts - по той же причине,
                                                            ;; что и у размерных линий строкой выше: котлован
                                                            ;; копают по настоящей оси прокола, а не по сдвинутой
                                                            ;; на 0,3 м оформительской копии провода.
                                                            (if (= Method "GNB")
                                                                (LEP:PlaceGnbPits P1Ent P1Pt P2Ent P2Pt SubVertsRaw RouteID)
                                                            )

                                                            ;; "+ подъём кабеля по опоре" на ОБЕИХ опорах КЛ-пролёта
                                                            ;; (по просьбе пользователя 2026-07-22).
                                                            (if (= (cdr LineType) "KL")
                                                                (progn
                                                                    (LEP:AddKLPoleNote P1Ent)
                                                                    (LEP:AddKLPoleNote P2Ent)
                                                                )
                                                            )
                                                        )
                                                    )
                                                )
                                            )
                                        )
                                    ) ; закрывает "if (< (length SubVerts) 2)"
                                    ) ; закрывает NEW-2 (progn "маршрут найден")
                                ) ; закрывает "if (not Route)"
                            ) ; закрывает NEW-1 (progn "трассы совпали")
                        ) ; закрывает "if (/= RouteID RouteID2)"
                    ) ; закрывает A (progn "if P2" then-ветка)
                ) ; закрывает "if P2"
            ) ; закрывает лямбду vl-catch-all-apply
             '())
        )

        (if (vl-catch-all-error-p LEP-CatchResult)
            (princ
                (strcat
                    "\n[LEP-SPAN] Ошибка на этом пролёте, пропускаю и продолжаю: "
                    (vl-catch-all-error-message LEP-CatchResult)
                )
            )
        )

        (setq P1 (LEP:PickPole "\nПервая опора пролёта (Enter - закончить): "))
    )

    (setvar "OSMODE" OldOs)

    (setq *error* OldError)
    (LEP:PrintFooter)
    (princ)
)
 
 
;=====================================================================
; C:LEP-SPAN-REPAIR - "чинилка" подписей пролётов
;
; ✅ ДОБАВЛЕНО 2026-07-22, по просьбе пользователя. Проблема: подпись
; пролёта теперь может быть ОБЩЕЙ на несколько пролётов одной марки
; (LEP:FinalizeSpanLabel, объединение подписей). Если пользователь
; стирает пролёт ВРУЧНУЮ обычной командой AutoCAD `ERASE` (рамкой или
; секущей рамкой, а не отдельной командой удаления пролёта - её в
; проекте пока нет) и рамка заодно зацепила саму подпись - у ОСТАВШИХСЯ
; пролётов группы `LABELHANDLE` начинает указывать на уже стёртый
; объект. Подпись у них пропадает целиком, хотя сами пролёты никто не
; трогал (подтверждено пользователем: "удалил командой erase").
;
; Эта команда сканирует ВСЕ пролёты на чертеже (все трассы разом - "по
; маршрутам", не по одному) и для каждого проверяет: резолвится ли его
; `LABELHANDLE` в реально существующий объект (`handent`). Если нет
; (поле пустое, или объект стёрт) - пролёт "голый", нужно чинить.
;
; ПОЧИНКА - переиспользует LEP:FinalizeSpanLabel ЦЕЛИКОМ, без
; дублирования логики объединения: у "голого" пролёта уже есть вся
; нужная информация в его собственной XDATA (POLE1HANDLE/POLE2HANDLE/
; WIRE/STATUS/ROUTE) - функции всё равно, был ли пролёт только что
; создан командой LEP-SPAN, или существовал давно и просто "осиротел".
; Она сама найдёт соседей, подхватит их текущие (тоже, возможно,
; осиротевшие - см. ниже) группы через LEP:FindGroupMembers, удалит
; всё что найдёт по старым хендлам (если те ещё существуют - если нет,
; просто пропустит удаление, ничего не сломается) и поставит одну
; новую подпись на всех.
;
; ⚠️ Если "голых" пролётов в одной группе НЕСКОЛЬКО (весь предыдущий
; общий label был стёрт разом) - после починки ПЕРВОГО пролёта в цикле
; вся группа получает новый LABELHANDLE, поэтому остальные пролёты той
; же группы, дойдя до них в цикле, уже окажутся "не голыми" и будут
; корректно пропущены - двойной работы не происходит.
;
; ⚠️ ЧЕГО ЭТА КОМАНДА НЕ ЧИНИТ (честно, по обсуждению с пользователем):
; если пролёт заменили на другую марку/тип, но СТАРУЮ общую подпись
; соседей не стёрли - она физически ВСЁ ЕЩЁ СУЩЕСТВУЕТ (просто
; показывает уже неверную суммарную длину/положение). `handent` для
; неё вернёт валидный объект, значит с точки зрения этой команды
; пролёт "не голый", чинить нечего - такую, ВИЗУАЛЬНО присутствующую,
; но текстово неверную подпись пользователю придётся стереть руками
; самому (это уже проговорено и принято - "что-то надо и ручками
; делать").
;=====================================================================

(defun C:LEP-SPAN-REPAIR (/ SS i Ent LabelHandle RouteID P1Handle P2Handle WireName Status
                            TypeCode RouteCache RouteEntry Route Verts Count)

    (LEP:PrintHeader "Проверка и восстановление подписей пролётов")

    (setq Count 0)
    (setq RouteCache nil) ; ((RouteID . (Route . Verts)) ...) - не сканировать слой маршрутов заново на каждый пролёт одной трассы

    (setq SS
        (ssget "_X"
            (list
                '(0 . "LWPOLYLINE")
                (cons 8
                    (strcat
                        *LEP-Layer-Proj-VL* "," *LEP-Layer-Exist-VL* ","
                        *LEP-Layer-Proj-KL* "," *LEP-Layer-Exist-KL*
                    )
                )
            )
        )
    )

    (if SS
        (progn
            (setq i 0)
            (repeat (sslength SS)
                (setq Ent (ssname SS i))
                (setq LabelHandle (LEP:GetDataValue Ent "LABELHANDLE"))

                ;; "Голый" пролёт - LABELHANDLE отсутствует вообще, либо
                ;; указывает на уже стёртый объект (handent вернёт nil).
                (if (or (not LabelHandle) (not (handent LabelHandle)))
                    (progn
                        (setq RouteID    (LEP:GetDataValue Ent "ROUTE"))
                        (setq P1Handle   (LEP:GetDataValue Ent "POLE1HANDLE"))
                        (setq P2Handle   (LEP:GetDataValue Ent "POLE2HANDLE"))
                        (setq WireName   (LEP:GetDataValue Ent "WIRE"))
                        (setq Status     (LEP:GetDataValue Ent "STATUS"))

                        (if (and RouteID P1Handle P2Handle WireName Status)
                            (progn
                                (setq RouteEntry (assoc RouteID RouteCache))
                                (if RouteEntry
                                    (setq Verts (cdr (cdr RouteEntry)))
                                    (progn
                                        (setq Route (LEP:FindRouteByID RouteID))
                                        (if Route
                                            (progn
                                                (setq Verts (LEP:GetVertices Route))
                                                (setq RouteCache (append RouteCache (list (cons RouteID (cons Route Verts)))))
                                            )
                                            (setq Verts nil)
                                        )
                                    )
                                )

                                (if Verts
                                    (progn
                                        (setq TypeCode (LEP:GetSpanTypeCode Ent))
                                        (LEP:FinalizeSpanLabel Ent Verts P1Handle P2Handle TypeCode WireName Status)
                                        (setq Count (1+ Count))
                                    )
                                    (princ (strcat "\n[LEP-SPAN-REPAIR] Не найдена трасса " RouteID " для одного из пролётов - пропускаю."))
                                )
                            )
                            (princ "\n[LEP-SPAN-REPAIR] У пролёта не хватает данных (старый пролёт без POLE1HANDLE/POLE2HANDLE - создан до этой правки?) - пропускаю.")
                        )
                    )
                )
                (setq i (1+ i))
            )
        )
    )

    (princ (strcat "\n[LEP-SPAN-REPAIR] Восстановлено подписей: " (itoa Count)))
    (LEP:PrintFooter)
    (princ)
)


;=====================================================================
; LEP:SelectAllSpans     (НОВАЯ 2026-08-20)
;
; Набор ВСЕХ пролётов чертежа - ВЛ и КЛ, проектируемых и существующих,
; одним ssget по четырём слоям через запятую.
;
; Ровно этот же ssget уже стоял ЧЕТЫРЬМЯ копиями в этом файле
; (LEP:GetSpanNeighbors, LEP:FindGroupMembers, LEP:FindSamePolePairSpans,
; C:LEP-SPAN-REPAIR). Пятую копию заводить не стал - по правилу проекта
; "перед добавлением новой функции проверь, нет ли уже похожей".
; Старые четыре сознательно НЕ переписаны на неё: они работают, а
; трогать рабочий код объединения подписей ради косметики - лишний
; риск на ровном месте.
;
; ⚠️ Возвращает набор ВСЕХ полилиний на этих слоях, а не только
; пролётов с XDATA. Отбор по TYPE="SPAN" - забота вызывающей стороны:
; на слой пролёта могла попасть и нарисованная руками линия.
;=====================================================================

(defun LEP:SelectAllSpans (/)
    (ssget "_X"
        (list
            '(0 . "LWPOLYLINE")
            (cons 8
                (strcat
                    *LEP-Layer-Proj-VL* "," *LEP-Layer-Exist-VL* ","
                    *LEP-Layer-Proj-KL* "," *LEP-Layer-Exist-KL*
                )
            )
        )
    )
)


;=====================================================================
; C:LEP-SPAN-WIRE - СМЕНА МАРКИ ПРОВОДА/КАБЕЛЯ У ГОТОВЫХ ПРОЛЁТОВ
;
; ✅ ДОБАВЛЕНО 2026-08-20 по прямой просьбе пользователя: "линия в 500 м
; уже размечена пролётами, а вдруг надо сменить СИП-2 70 мм2 на 95".
;
; ДО ЭТОЙ КОМАНДЫ такое лечилось только перечерчиванием всех пролётов
; заново. Отредактировать текст выноски руками мало: марка живёт в ДВУХ
; местах - в XDATA пролёта (WIRE/SECTION) и в тексте подписи. Правка
; одного текста дала бы чертёж с новой маркой и ведомость со старой,
; причём БЕЗ ЕДИНОГО ПРИЗНАКА ошибки на экране.
;
; ЧТО МЕНЯЕТСЯ: ровно WIRE + SECTION в XDATA и текст подписи.
; ЧТО НЕ МЕНЯЕТСЯ И ПОЧЕМУ (решение пользователя 2026-08-20):
;   - длины (LENGTH/RAWLENGTH/RESERVE) - считаются из геометрии, класса
;     напряжения и способа прокладки; от марки не зависят;
;   - число фаз - от класса напряжения;
;   - слой, цвет, толщина - от класса x статуса x способа прокладки;
;   - котлованы ГНБ и "+ подъём кабеля по опоре" - от типа прокладки.
; Сменился провод - трасса осталась той же длины. Пересчёт длин задним
; числом сюда не втаскиваем: это отдельная задача.
;
; ⚠️ ВЛ <-> КЛ ЭТОЙ КОМАНДОЙ НЕ МЕНЯЮТСЯ. Там другой слой, другой
; способ прокладки, другие запасы, котлованы и подписи опор - это
; перечерчивание, а не смена марки. Поэтому список марок-целей
; берётся ПО ТИПУ уже нарисованных пролётов, и попасть в него марка
; чужого типа физически не может.
;
; ⚠️ ГЛАВНАЯ ЛОВУШКА - ОБЪЕДИНЁННЫЕ ПОДПИСИ. Подпись у нас общая на
; группу пролётов одной марки (LEP:FinalizeSpanLabel). Наивное "сменил
; XDATA у части группы - позвал Finalize" сломало бы две вещи сразу:
;   1. LEP:FindGroupMembers собирает группу ПО LABELHANDLE и марку НЕ
;      ПРОВЕРЯЕТ - значит в новую группу затянуло бы и соседей со
;      СТАРОЙ маркой, и они получили бы чужую подпись;
;   2. у тех, кого не затянуло, LABELHANDLE указывал бы на стёртую
;      подпись, и они остались бы без неё вовсе (ровно тот случай,
;      ради которого существует C:LEP-SPAN-REPAIR).
;
; ПОЭТОМУ ПОРЯДОК ДЕЙСТВИЙ ТАКОЙ И ТОЛЬКО ТАКОЙ:
;   1. собрать выбранные пролёты (Targets);
;   2. добрать к ним ВСЕХ соседей по их текущим группам подписей
;      (Affected) - даже тех, чью марку мы не меняем;
;   3. стереть старые подписи этих групп и ОБНУЛИТЬ LABELHANDLE у всех
;      участников - после этого ни одна группа не может собраться по
;      устаревшей связи;
;   4. сменить марку у Targets;
;   5. пересобрать подписи, вызвав LEP:FinalizeSpanLabel по КАЖДОМУ
;      участнику Affected.
;
; ⚠️ Почему на шаге 5 можно звать Finalize подряд по всем, не боясь
; лишних подписей: каждый вызов удаляет подписи всей группы, которую
; найдёт по АКТУАЛЬНЫМ хендлам, и ставит одну новую. Цепочка A-B-C
; собирается за проход: Finalize(A) даёт подпись на A+B, дальше
; Finalize(C) подхватывает уже собранную группу через новый
; LABELHANDLE соседа B и переставляет одну общую на A+B+C. Лишняя
; работа есть (выноска создаётся и удаляется несколько раз), лишних
; объектов на чертеже не остаётся.
;
; ⚠️ РАЗНЫЕ КЛАССЫ НАПРЯЖЕНИЯ В ОДНОЙ ВЫБОРКЕ - ОТКАЗ (решение
; пользователя). Списки марок у 10, 6 и 0,4 кВ разные, и молча
; положить СИП-2 на десятку - именно та тихая ошибка, которую потом
; ловят на объекте, а не на чертеже. Проверка касается только ВЛ: у
; КЛ список марок один на все классы, делить там нечего.
;
; ⚠️ Ведомость после смены надо ВЫГРУЗИТЬ ЗАНОВО (LEP-REPORT) - старый
; CSV сам себя не перепишет.
;=====================================================================

(defun C:LEP-SPAN-WIRE (/ Scope SS Targets Affected Ent i PickEnt PickRoute
                          OldWire Marks Filtered Entry MarkChoice NewChoice NewWire
                          NewSection RouteCache RouteID Route Verts VClass
                          TypeCode TypeSet VClassSet WireList OldHandles H
                          OldEnt M Changed Rebuilt Skipped Status P1Handle
                          P2Handle Answer Bad)

    (LEP:PrintHeader "Смена марки провода/кабеля")

    ;;-----------------------------------------------------------------
    ;; ШАГ 1. Область действия.
    ;;-----------------------------------------------------------------
    (setq Scope
        (LEP:ChooseFromList
            (list
                (cons "Весь чертёж" "ALL")
                (cons "Один маршрут (клик по любому его пролёту)" "ROUTE")
                (cons "Выбрать пролёты рамкой" "PICK")
            )
            "Где менять марку"
        )
    )

    (if (not Scope)
        (progn
            (princ "\n[LEP-SPAN-WIRE] Отменено.")
            (LEP:PrintFooter)
        )
        (progn

            ;;---------------------------------------------------------
            ;; ШАГ 2. Набор пролётов-кандидатов.
            ;;---------------------------------------------------------
            (setq PickRoute nil)

            (cond

                ((= (cdr Scope) "ALL")
                    (setq SS (LEP:SelectAllSpans))
                )

                ((= (cdr Scope) "PICK")
                    ;; Фильтр по слоям стоит прямо в ssget - в выбор
                    ;; рамкой иначе попала бы вся подоснова, и дальше
                    ;; пришлось бы объяснять пользователю, почему
                    ;; "выбрано 400 объектов, изменено 12".
                    (princ "\n[LEP-SPAN-WIRE] Выберите пролёты (рамкой или по одному), затем Enter.")
                    (setq SS
                        (ssget
                            (list
                                '(0 . "LWPOLYLINE")
                                (cons 8
                                    (strcat
                                        *LEP-Layer-Proj-VL* "," *LEP-Layer-Exist-VL* ","
                                        *LEP-Layer-Proj-KL* "," *LEP-Layer-Exist-KL*
                                    )
                                )
                            )
                        )
                    )
                )

                (t
                    ;; Один маршрут: кликаем ЛЮБОЙ его пролёт и берём
                    ;; ROUTE из XDATA. По самой полилинии маршрута
                    ;; кликать нельзя - слой маршрутов обычно скрыт
                    ;; (LEP-ROUTEVIS), а пролёты видны всегда.
                    (setq PickEnt (car (entsel "\n[LEP-SPAN-WIRE] Клик по любому пролёту нужного маршрута: ")))
                    (if (and PickEnt (= (LEP:GetDataValue PickEnt "TYPE") "SPAN"))
                        (progn
                            (setq PickRoute (LEP:GetDataValue PickEnt "ROUTE"))
                            (setq SS (LEP:SelectAllSpans))
                            (princ (strcat "\n[LEP-SPAN-WIRE] Маршрут: " (if PickRoute PickRoute "не определён")))
                        )
                        (progn
                            (princ "\n[LEP-SPAN-WIRE] Это не пролёт - кликните по линии провода или кабеля.")
                            (setq SS nil)
                        )
                    )
                )
            )

            ;;---------------------------------------------------------
            ;; ШАГ 3. Отбор настоящих пролётов (TYPE="SPAN"), при
            ;; необходимости - ещё и по маршруту. На слое провода могла
            ;; оказаться и линия, нарисованная руками: у неё нет XDATA,
            ;; и трогать её нельзя.
            ;;---------------------------------------------------------
            (setq Targets nil)
            (if SS
                (progn
                    (setq i 0)
                    (repeat (sslength SS)
                        (setq Ent (ssname SS i))
                        (if (and (= (LEP:GetDataValue Ent "TYPE") "SPAN")
                                 (or (not PickRoute)
                                     (= (LEP:GetDataValue Ent "ROUTE") PickRoute)
                                 )
                            )
                            (setq Targets (append Targets (list Ent)))
                        )
                        (setq i (1+ i))
                    )
                )
            )

            (if (not Targets)
                (progn
                    (princ "\n[LEP-SPAN-WIRE] Пролётов не найдено - менять нечего.")
                    (LEP:PrintFooter)
                )
                (progn

                    ;;-------------------------------------------------
                    ;; ШАГ 4. Какие марки РЕАЛЬНО лежат в выборке.
                    ;;
                    ;; Список строится по чертежу, а не по конфигу, и
                    ;; это принципиально: на чертеже могут лежать марки
                    ;; из прежних версий конфига, которых в текущих
                    ;; списках уже нет. Показать надо то, что есть.
                    ;;-------------------------------------------------
                    (setq Marks nil)
                    (foreach Ent Targets
                        (setq OldWire (LEP:GetDataValue Ent "WIRE"))
                        (if OldWire
                            (progn
                                (setq Entry (assoc OldWire Marks))
                                (if Entry
                                    (setq Marks (subst (cons OldWire (1+ (cdr Entry))) Entry Marks))
                                    (setq Marks (append Marks (list (cons OldWire 1))))
                                )
                            )
                        )
                    )

                    ;; ⚠️ Пустой список марок - реальный случай: на слое
                    ;; провода могли оказаться линии без XDATA. Меню из
                    ;; нуля пунктов зациклило бы LEP:ChooseFromList на
                    ;; "нет такого номера" (выход только через Enter),
                    ;; поэтому отсекаем ДО вызова меню.
                    (setq MarkChoice
                        (if Marks
                            (LEP:ChooseFromList
                                (mapcar
                                    '(lambda (Item)
                                        (cons
                                            (strcat (car Item) "  -  пролётов: " (itoa (cdr Item)))
                                            (car Item)
                                        )
                                     )
                                    Marks
                                )
                                "Какую марку меняем"
                            )
                            (progn
                                (princ "\n[LEP-SPAN-WIRE] У найденных пролётов нет марки в XDATA - менять нечего.")
                                nil
                            )
                        )
                    )

                    (if (not MarkChoice)
                        (progn
                            (princ "\n[LEP-SPAN-WIRE] Отменено.")
                            (LEP:PrintFooter)
                        )
                        (progn

                            (setq OldWire (cdr MarkChoice))

                            ;; Оставляем только пролёты выбранной марки.
                            (setq Filtered nil)
                            (foreach Ent Targets
                                (if (= (LEP:GetDataValue Ent "WIRE") OldWire)
                                    (setq Filtered (append Filtered (list Ent)))
                                )
                            )
                            (setq Targets Filtered)

                            ;;-----------------------------------------
                            ;; ШАГ 5. Тип прокладки и класс напряжения.
                            ;; Кэш маршрутов - чтобы не сканировать слой
                            ;; маршрутов заново на каждый пролёт
                            ;; (тот же приём, что в C:LEP-SPAN-REPAIR).
                            ;; Формат: ((RouteID Route Verts VClass) ...)
                            ;;-----------------------------------------
                            (setq TypeSet nil)
                            (setq VClassSet nil)
                            (setq RouteCache nil)
                            (setq Bad nil)

                            (foreach Ent Targets

                                (setq TypeCode (LEP:GetSpanTypeCode Ent))
                                (if (not (member TypeCode TypeSet))
                                    (setq TypeSet (append TypeSet (list TypeCode)))
                                )

                                (setq RouteID (LEP:GetDataValue Ent "ROUTE"))
                                (if (not RouteID)
                                    (setq Bad "у одного из пролётов нет маршрута в XDATA (пролёт из очень старой версии программы)")
                                    (progn
                                        (setq Entry (assoc RouteID RouteCache))
                                        (if (not Entry)
                                            (progn
                                                (setq Route (LEP:FindRouteByID RouteID))
                                                (if Route
                                                    (progn
                                                        (setq Entry
                                                            (list RouteID
                                                                  Route
                                                                  (LEP:GetVertices Route)
                                                                  (LEP:GetDataValue Route "VCLASS")
                                                            )
                                                        )
                                                        (setq RouteCache (append RouteCache (list Entry)))
                                                    )
                                                    (setq Bad (strcat "на чертеже не найден маршрут " RouteID " - без него подпись не пересобрать"))
                                                )
                                            )
                                        )
                                        ;; Класс собираем ТОЛЬКО у ВЛ:
                                        ;; у КЛ список марок один на все
                                        ;; классы, и делить там нечего.
                                        (if (and Entry (= TypeCode "VL"))
                                            (progn
                                                (setq VClass (cadddr Entry))
                                                (if (not (member VClass VClassSet))
                                                    (setq VClassSet (append VClassSet (list VClass)))
                                                )
                                            )
                                        )
                                    )
                                )
                            )

                            ;; Смешение ВЛ и КЛ в одной выборке в норме
                            ;; невозможно (марки провода и кабеля не
                            ;; совпадают текстом), но если данные битые -
                            ;; лучше отказаться, чем положить кабель на
                            ;; воздушный слой.
                            (if (and (not Bad) (> (length TypeSet) 1))
                                (setq Bad "в выборку попали и ВЛ, и КЛ - это разные слои и разные способы прокладки")
                            )
                            (if (and (not Bad) (> (length VClassSet) 1))
                                (setq Bad "в выборку попали ВЛ разных классов напряжения - у них РАЗНЫЕ списки марок")
                            )

                            (if Bad
                                (progn
                                    (princ (strcat "\n[LEP-SPAN-WIRE] ⚠️ ОТМЕНА: " Bad "."))
                                    (princ "\n[LEP-SPAN-WIRE] Что делать: сузьте область - выберите один маршрут или отметьте нужные пролёты рамкой.")
                                    (LEP:PrintFooter)
                                )
                                (progn

                                    ;;---------------------------------
                                    ;; ШАГ 6. Куда меняем. Список - тот
                                    ;; же, что и при создании пролёта
                                    ;; (C:LEP-SPAN), по типу и классу.
                                    ;;---------------------------------
                                    (setq TypeCode (car TypeSet))
                                    (setq VClass (car VClassSet))

                                    (if (= TypeCode "VL")
                                        (cond
                                            ((= VClass "10") (setq WireList *LEP-WireTypes-VL-10*))
                                            ((= VClass "6")  (setq WireList *LEP-WireTypes-VL-6*))
                                            (t               (setq WireList *LEP-WireTypes-VL-04*))
                                        )
                                        (setq WireList *LEP-WireTypes-KL*)
                                    )

                                    (setq NewChoice (LEP:ChooseFromList WireList "На какую марку меняем"))

                                    (cond

                                        ((not NewChoice)
                                            (princ "\n[LEP-SPAN-WIRE] Отменено.")
                                            (LEP:PrintFooter)
                                        )

                                        ((= (car NewChoice) OldWire)
                                            (princ "\n[LEP-SPAN-WIRE] Это та же самая марка - менять нечего.")
                                            (LEP:PrintFooter)
                                        )

                                        (t
                                            (setq NewWire (car NewChoice))
                                            (setq NewSection (cdr NewChoice))

                                            ;;-------------------------
                                            ;; ШАГ 7. Подтверждение.
                                            ;; Операция массовая и через
                                            ;; U откатывается одним
                                            ;; куском только пока не
                                            ;; начал чертить дальше -
                                            ;; спросить дешевле.
                                            ;;
                                            ;; ⚠️ Скобки в строке
                                            ;; getkword - ТОЛЬКО список
                                            ;; ответов, префикс идёт
                                            ;; отдельным princ ДО
                                            ;; initget (иначе Dynamic
                                            ;; Input покажет у курсора
                                            ;; "LEP-SPAN-WIRE" вместо
                                            ;; "Да"/"Нет").
                                            ;;-------------------------
                                            (princ
                                                (strcat
                                                    "\n[LEP-SPAN-WIRE] Меняю \""
                                                    OldWire "\" -> \"" NewWire
                                                    "\" на пролётах: " (itoa (length Targets))
                                                )
                                            )
                                            (initget "Да Нет")
                                            (setq Answer (getkword "\nМеняем? [Да/Нет] <Да>: "))

                                            (if (= Answer "Нет")
                                                (progn
                                                    (princ "\n[LEP-SPAN-WIRE] Отменено.")
                                                    (LEP:PrintFooter)
                                                )
                                                (progn

                                                    ;;-----------------
                                                    ;; ШАГ 8. Кто ещё
                                                    ;; сидит в тех же
                                                    ;; группах подписей.
                                                    ;; Подробное "зачем"
                                                    ;; - в шапке команды.
                                                    ;;-----------------
                                                    (setq Affected Targets)
                                                    (setq OldHandles nil)

                                                    (foreach Ent Targets
                                                        (setq H (LEP:GetDataValue Ent "LABELHANDLE"))
                                                        (if (and H (not (member H OldHandles)))
                                                            (progn
                                                                (setq OldHandles (append OldHandles (list H)))
                                                                (foreach M (LEP:FindGroupMembers H (LEP:GetDataValue Ent "ROUTE"))
                                                                    (if (not (member M Affected))
                                                                        (setq Affected (append Affected (list M)))
                                                                    )
                                                                )
                                                            )
                                                        )
                                                    )

                                                    ;;-----------------
                                                    ;; ШАГ 9. Снести
                                                    ;; старые подписи и
                                                    ;; ОБНУЛИТЬ связь с
                                                    ;; ними у всех
                                                    ;; участников.
                                                    ;;
                                                    ;; ⚠️ handent на nil
                                                    ;; ПАДАЕТ - в списке
                                                    ;; только непустые
                                                    ;; хендлы, см. шаг 8.
                                                    ;; Хендл может
                                                    ;; указывать на уже
                                                    ;; стёртый объект -
                                                    ;; тогда handent
                                                    ;; вернёт nil, и это
                                                    ;; нормально.
                                                    ;;-----------------
                                                    (foreach H OldHandles
                                                        (setq OldEnt (handent H))
                                                        (if OldEnt (entdel OldEnt))
                                                    )
                                                    (foreach Ent Affected
                                                        (LEP:SetSpanLabelHandle Ent nil)
                                                    )

                                                    ;;-----------------
                                                    ;; ШАГ 10. Собственно
                                                    ;; смена марки.
                                                    ;;-----------------
                                                    (setq Changed 0)
                                                    (foreach Ent Targets
                                                        (LEP:SetSpanWire Ent NewWire NewSection)
                                                        (setq Changed (1+ Changed))
                                                    )

                                                    ;;-----------------
                                                    ;; ШАГ 11. Пересборка
                                                    ;; подписей. Марка
                                                    ;; берётся из XDATA
                                                    ;; КАЖДОГО пролёта:
                                                    ;; у изменённых она
                                                    ;; новая, у соседей
                                                    ;; осталась старая, и
                                                    ;; группы разойдутся
                                                    ;; сами собой.
                                                    ;;-----------------
                                                    (setq Rebuilt 0)
                                                    (setq Skipped 0)

                                                    (foreach Ent Affected

                                                        (setq RouteID  (LEP:GetDataValue Ent "ROUTE"))
                                                        (setq Status   (LEP:GetDataValue Ent "STATUS"))
                                                        (setq P1Handle (LEP:GetDataValue Ent "POLE1HANDLE"))
                                                        (setq P2Handle (LEP:GetDataValue Ent "POLE2HANDLE"))
                                                        (setq Entry    (assoc RouteID RouteCache))

                                                        ;; Соседи по группе - того же маршрута
                                                        ;; (LEP:FindGroupMembers сверяет ROUTE),
                                                        ;; так что в кэше они уже есть. Но если
                                                        ;; вдруг нет - добираем, а не падаем.
                                                        (if (and RouteID (not Entry))
                                                            (progn
                                                                (setq Route (LEP:FindRouteByID RouteID))
                                                                (if Route
                                                                    (progn
                                                                        (setq Entry
                                                                            (list RouteID
                                                                                  Route
                                                                                  (LEP:GetVertices Route)
                                                                                  (LEP:GetDataValue Route "VCLASS")
                                                                            )
                                                                        )
                                                                        (setq RouteCache (append RouteCache (list Entry)))
                                                                    )
                                                                )
                                                            )
                                                        )

                                                        (setq Verts (if Entry (caddr Entry) nil))

                                                        (if (and Verts P1Handle P2Handle Status)
                                                            (progn
                                                                (LEP:FinalizeSpanLabel
                                                                    Ent
                                                                    Verts
                                                                    P1Handle
                                                                    P2Handle
                                                                    (LEP:GetSpanTypeCode Ent)
                                                                    (LEP:GetDataValue Ent "WIRE")
                                                                    Status
                                                                )
                                                                (setq Rebuilt (1+ Rebuilt))
                                                            )
                                                            (setq Skipped (1+ Skipped))
                                                        )
                                                    )

                                                    ;;-----------------
                                                    ;; ШАГ 12. Отчёт.
                                                    ;;-----------------
                                                    (princ (strcat "\n[LEP-SPAN-WIRE] Изменено пролётов: " (itoa Changed)))
                                                    (princ (strcat "\n[LEP-SPAN-WIRE] Пересобрано подписей: " (itoa Rebuilt)))

                                                    (if (> Skipped 0)
                                                        (progn
                                                            (princ (strcat "\n[LEP-SPAN-WIRE] ⚠️ Без подписи осталось пролётов: " (itoa Skipped)))
                                                            (princ "\n[LEP-SPAN-WIRE] У них не хватает данных в XDATA (старые пролёты). Попробуйте LEP-SPAN-REPAIR.")
                                                        )
                                                    )

                                                    (princ "\n[LEP-SPAN-WIRE] ⚠️ Длины НЕ пересчитывались - от марки они не зависят.")
                                                    (princ "\n[LEP-SPAN-WIRE] ⚠️ Ведомость нужно выгрузить заново (LEP-REPORT).")
                                                    (LEP:PrintFooter)
                                                )
                                            )
                                        )
                                    )
                                )
                            )
                        )
                    )
                )
            )
        )
    )

    (princ)
)


(princ "\nLEP-SPAN v1.8 загружен (геометрическое определение маршрута, параллельный сдвиг проводов, Т-образное подключение, LEP-SPAN-REPAIR, LEP-SPAN-WIRE).")
(princ)
