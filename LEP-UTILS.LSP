;=====================================================================
;
;   ПРОЕКТ:      LEP
;
;   ФАЙЛ:        LEP-UTILS.LSP
;
;   ВЕРСИЯ:      0.5  (LEP:GetMLeaderText/LEP:SetMLeaderText - чтение и
;                замена текста готовой выноски целиком, вынесены из
;                LEP:AppendMLeaderText для переноса подписи в
;                C:LEP-POLE-MOVE, Claude, 2026-07-28)
;   0.4  (LEP:AppendMLeaderText - дописать строку в готовую
;                выноску, для ПУ на сущ. опоре, Claude, 2026-07-15)
;   0.3  (LEP:BringToFront - DRAWORDER Front для подписей/
;                размеров, Claude, 2026-07-15)
;   0.2  (LEP:SetMLeaderBackgroundMask - фон под текстом
;                выносок, Claude, 2026-07-15)
;   0.1
;
;   НАЗНАЧЕНИЕ:
;
;   Общие служебные функции проекта.
;
;   Данные функции не являются самостоятельными командами.
;
;   Они используются всеми остальными модулями проекта.
;
;=====================================================================



;=====================================================================
;                     LEP:LayerExists
;
; Проверяет существование слоя.
;
; Вход:
;   LayerName
;
; Выход:
;   T
;   nil
;
;=====================================================================

(defun LEP:LayerExists (LayerName)

    (if (tblsearch "LAYER" LayerName)
        T
        nil
    )

)



;=====================================================================
;                     LEP:SetCurrentLayer
;
; Делает слой текущим.
;
;=====================================================================

(defun LEP:SetCurrentLayer (LayerName)

    (if (LEP:LayerExists LayerName)

        (setvar "CLAYER" LayerName)

        (princ
            (strcat
                "\nОшибка. Слой "
                LayerName
                " не существует."
            )
        )

    )

)



;=====================================================================
;                     LEP:PrintHeader
;
; Красивый заголовок команды.
;
;=====================================================================

(defun LEP:PrintHeader (Title)

    (princ "\n")

    (princ "==========================================")

    (princ
        (strcat
            "\n"
            Title
        )
    )

    (princ "\n==========================================")

)



;=====================================================================
;                     LEP:RoundUp
;
; Округление ВВЕРХ до целого (математический "потолок"/ceiling).
; Нужно для длины провода/кабеля с запасом - для закупки материала
; всегда округляем в большую сторону, никогда не в меньшую (иначе
; можно купить впритык и не хватит).
;
; AutoLISP не умеет ceiling из коробки, только fix (обрезает дробную
; часть в сторону нуля) - поэтому: если дробный остаток есть, целая
; часть + 1, если остатка нет (число и так целое) - как есть.
; Сравнение с крошечным эпсилон (1e-9), а не напрямую с 0 - иначе
; накопленная погрешность вещественных чисel (например Value
; получилось 45.00000001 вместо ровно 45.0) ошибочно округлила бы
; вверх лишний раз.
;=====================================================================

(defun LEP:RoundUp (Value / IntPart)

    (setq IntPart (fix Value))

    (if (> (- Value IntPart) 1e-9)
        (1+ IntPart)
        IntPart
    )

)



;=====================================================================
;                     LEP:RoundNearest
;
; Округление ДО БЛИЖАЙШЕГО целого по обычным правилам математики
; (0.5 и больше - вверх, меньше - вниз). Для расстояния между опорами
; на размерной линии (LEP-SPAN) - это просто читаемое число для
; человека, не запас материала, поэтому округляем как в жизни, а не
; всегда вверх.
;=====================================================================

(defun LEP:RoundNearest (Value)

    (fix (+ Value 0.5))

)



;=====================================================================
;                     LEP:RoundLength
;
; ЕДИНОЕ правило округления ДЛИНЫ В МЕТРАХ на весь проект. Все длины
; провода/кабеля/траншеи - и в подписях на чертеже, и в размерных
; линиях, и в ведомости - округляются ТОЛЬКО через эту функцию.
;
; ✅ ДОБАВЛЕНО 2026-08-05. Причина - реальная находка пользователя:
; один и тот же пролёт 46,4958 м был подписан выноской "L=47 м"
; (LEP:RoundUp) и размерной линией "46 м" (LEP:RoundNearest) - два
; разных числа про одну и ту же величину, рядом на одном чертеже.
; Раньше это были два независимых решения в двух разных местах кода,
; и ничто не мешало им разъехаться. Теперь правило одно и живёт здесь.
;
; ПРАВИЛО:
;   Value > *LEP-Round-UpThreshold*  -> вверх, но с допуском (LEP:RoundUp
;                                       от длины, уменьшенной на
;                                       *LEP-Round-UpTolerance*)
;   Value <= порога                  -> по матем. (LEP:RoundNearest)
;
; ✅ ДОПУСК ДОБАВЛЕН 2026-08-11. Находка пользователя: размерная линия
; с Measurement 50,0025 м подписана "51 м". Голый потолок поднимает
; число на целый метр из-за хвоста в 2,5 мм, который взялся не из
; геометрии трассы, а из того, что точка ставилась мышкой. Поэтому
; перед потолком из длины вычитается допуск: хвост не больше допуска
; считается нулём и число вверх не идёт.
;
;   50.0025 -> 50   (было 51)
;   50.09   -> 50
;   50.10   -> 50   (ровно допуск - ещё не поднимает)
;   50.11   -> 51
;   46.4958 -> 47   (как и раньше - хвост настоящий, почти полметра)
;
; ⚠️ Допуск НЕ применяется ниже порога: там и так работает обычная
; математика, которая вверх без причины не поднимает.
;
; Почему не просто "всегда вверх": на коротких длинах это врёт в разы.
; 1,1 м стал бы "2 м" - почти вдвое, и на чертеже такое читается как
; ошибка черчения, а не как запас. На 46 метрах лишние полметра не
; видит никто. Порог и подробное обоснование - в LEP-CONFIG.LSP.
;
; Почему не просто "всегда по математике": длина в ведомости - это
; сколько материала закупать. Округлить вниз значит недокупить, и это
; выяснится уже на монтаже.
;
; ⚠️ Разрыва на пороге НЕТ (проверял специально - пороговые правила
; часто его создают): 4.9 -> 5, ровно 5.0 -> 5, 5.05 -> 5, 5.2 -> 6.
; Функция монотонна, больший вход не может дать меньший выход - допуск
; этого не сломал: чуть выше порога потолок берётся уже от Value минус
; допуск, то есть от числа около самого порога, и даёт то же целое,
; что математическое округление на пороге.
;
; ⚠️ НЕ применять к штукам. LEP:RoundUp остаётся отдельной функцией и
; по-прежнему нужен там, где считаются ШТУКИ, а не метры - число труб
; на ГНБ-прокол (LEP-REPORT.LSP, ЭТАП 1.7). Полтрубы не купишь, там
; потолок обязателен ВСЕГДА, никаких порогов. LEP:RoundNearest тоже
; остаётся - он используется как страховка от накопленной погрешности
; при суммировании уже целых чисел (LEP:WriteMasterListBlock).
;=====================================================================

(defun LEP:RoundLength (Value)

    (if (> Value *LEP-Round-UpThreshold*)
        (LEP:RoundUp (- Value *LEP-Round-UpTolerance*))
        (LEP:RoundNearest Value)
    )

)



;=====================================================================
;                     LEP:PrintFooter
;
;=====================================================================

(defun LEP:PrintFooter ()

    (princ "\n==========================================")

    (princ "\nГотово.")

    (princ "\n==========================================")

)



;=====================================================================
;                     LEP:GetStatus
;
; Запрашивает статус объекта: Проект или Существующий. Общая функция
; для LEP-POLE (статус опоры) и LEP-SPAN (статус пролёта) - раньше
; была только в LEP-POLE.LSP, продублировали бы то же самое в
; LEP-SPAN, поэтому вынесено сюда.
;
; ObjectLabel - слово в родительном падеже для промпта, например
; "опоры" или "пролёта" ("Статус опоры [...]" / "Статус пролёта [...]").
;
; Возвращает "PROJECT" или "EXIST".
;=====================================================================

(defun LEP:GetStatus (ObjectLabel / Choice)

    (initget "Проект Сущ")
    (setq Choice
        (getkword (strcat "\nСтатус " ObjectLabel " [Проект/Сущ] <Проект>: "))
    )

    (if (or (not Choice) (= Choice "Проект"))
        "PROJECT"
        "EXIST"
    )

)



;=====================================================================
;                     LEP:ChooseFromList
;
; Универсальный выбор одного пункта из списка cons-пар (label . value)
; - номером в командной строке, с проверкой диапазона и повторным
; запросом при неверном вводе. Раньше была только в LEP-SPAN.LSP (для
; типа прокладки ВЛ/КЛ и марки провода/кабеля), продублировали бы
; то же самое в LEP-POLE для списка типов опор - поэтому вынесено
; сюда, общая для обоих модулей.
;
; КАЖДЫЙ ПУНКТ - НА ОТДЕЛЬНОЙ СТРОКЕ (раньше все пункты склеивались
; в одну длинную строку через два пробела - с 1-2 проводами это было
; незаметно, а со списком из 10 типов опор превращалось в нечитаемую
; простыню, которая переносится по ширине консоли как попало, а не
; в настоящий столбик).
;
; Возвращает: выбранную пару (cons Label Value) целиком, либо nil
; при отмене (Enter без числа). Если из пары нужно только имя
; (Label) - берите (car Result) у вызывающей стороны.
;=====================================================================

(defun LEP:ChooseFromList (ItemList PromptText / MenuText i Item Choice Result Valid)

    (setq MenuText "")
    (setq i 1)

    (foreach Item ItemList
        (setq MenuText (strcat MenuText "\n" (itoa i) "-" (car Item)))
        (setq i (1+ i))
    )

    (setq Result nil)
    (setq Valid nil)

    (while (not Valid)

        (initget 6)
        (setq Choice (getint (strcat MenuText "\n" PromptText ": ")))

        (cond
            ((not Choice)
             (setq Valid T)
            )
            ((or (< Choice 1) (> Choice (length ItemList)))
             (princ "\nНет такого номера, попробуйте ещё раз.")
            )
            (t
             (setq Result (nth (1- Choice) ItemList))
             (setq Valid T)
            )
        )
    )

    Result
)



;=====================================================================
; LEP:SetMLeaderBackgroundMask
;
; Включает фоновую маску текста у ОДНОЙ конкретной уже созданной
; выноски MULTILEADER (Ent - ename, обычно (entlast) сразу после
; (command "_.MLEADER" ...)). Значения групп - *LEP-MLeader-BgColorValue*/
; *LEP-MLeader-BgScale* в LEP-CONFIG.LSP - см. там ПОДРОБНОЕ
; обоснование, откуда взялись, и почему это НЕ настройка стиля
; (MLEADERSTYLE), а именно каждой отдельной выноски (⚠️ важно - если
; кто-то захочет "сделать один раз на весь чертёж", как остальные
; настройки MLEADER, - так не получится, у стиля нет такого поля).
;
; ⚠️ ПОЧЕМУ ЧЕРЕЗ РАЗБИЕНИЕ СПИСКА, А НЕ ПРОСТО assoc/subst: у сущности
; MULTILEADER вложенная структура (CONTEXT_DATA{ -> LEADER{ ->
; LEADER_LINE{), и коды ПОВТОРЯЮТСЯ (например (292 . 0) встречается
; ДВАЖДЫ - наше поле фона и не связанное с ним поле глубже в LEADER{).
; Обычный subst меняет ВСЕ вхождения с одинаковым значением - живым
; тестом 2026-07-15 поймано, что "слепой" subst портит и то, второе,
; чужое поле тоже. Поэтому здесь правится ТОЛЬКО "голова" списка -
; часть ДО первого маркера (302 . "LEADER{"), где реально лежат нужные
; нам поля (CONTEXT_DATA верхнего уровня) - хвост (сам LEADER{ со всей
; вложенностью) не трогается вообще, коллизия невозможна по построению.
;=====================================================================

(defun LEP:SetMLeaderBackgroundMask (Ent / EData Head Tail)

    (setq EData (entget Ent))
    (setq Head nil)
    (setq Tail EData)

    ;; Собираем "голову" - всё ДО первого маркера начала вложенного
    ;; LEADER{ - именно там, в CONTEXT_DATA верхнего уровня, лежат
    ;; нужные нам поля фона (91/141/291/292).
    (while (and Tail (not (equal (car Tail) (cons 302 "LEADER{"))))
        (setq Head (cons (car Tail) Head))
        (setq Tail (cdr Tail))
    )
    (setq Head (reverse Head))

    (setq Head (subst (cons 291 1) (assoc 291 Head) Head))
    (setq Head (subst (cons 292 1) (assoc 292 Head) Head))
    (setq Head (subst (cons 91 *LEP-MLeader-BgColorValue*) (assoc 91 Head) Head))
    (setq Head (subst (cons 141 *LEP-MLeader-BgScale*) (assoc 141 Head) Head))

    (entmod (append Head Tail))
)



;=====================================================================
; LEP:BringToFront
;
; Порядок отрисовки объекта - НАВЕРХ (DRAWORDER, опция Front) - чтобы
; подписи/размеры не оказывались визуально ПОД линиями/штриховкой
; подложки, если они случайно перекрылись на экране/печати. По
; просьбе пользователя 2026-07-15 - для ВСЕХ подписей (опор/маршрута/
; пролёта) и размерной линии пролёта, сразу после их создания.
;
; Через command, не entmod - DRAWORDER это не свойство самой
; сущности (нет отдельной DXF-группы "нарисовать выше/ниже"), а
; порядок в СПИСКЕ отрисовки чертежа целиком - штатно меняется только
; этой командой. Ent передаётся в command НАПРЯМУЮ как выбор объекта
; (без ssget/ssadd) - тот же приём, что уже работает в проекте для
; GEOMCONSTRAINT (LEP-POLE.LSP) - command принимает одиночный ename
; на месте "Select objects:" без обёртки в набор.
;=====================================================================

(defun LEP:BringToFront (Ent / )
    (command "_.draworder" Ent "" "_Front")
)



;=====================================================================
; LEP:AppendMLeaderText
;
; Дописывает ДОПОЛНИТЕЛЬНУЮ строку в конец текста УЖЕ СУЩЕСТВУЮЩЕЙ
; выноски MLEADER (LabelEnt) - через код разрыва абзаца "\P" (тот же
; приём, что и в двухстрочной подписи опоры, LEP-POLE.LSP). Нужна для
; "ПУ на существующую опору" (LEP-END.LSP, 2026-07-15) - вместо новой
; отдельной подписи дописываем строку прямо в подпись самой опоры.
;
; Подтверждено ЖИВЫМ ТЕСТОМ 2026-07-15 (пользователь, реальная опора):
; текст выноски лежит в группе DXF 304 - НО у MULTILEADER эта же
; группа 304 встречается в записи ЕЩЁ РАЗ, глубже, как служебный
; маркер начала вложенного блока "LEADER_LINE{" (та же природа
; ловушки, что уже ловили на группе 292 при работе над фоном подписи,
; см. LEP:SetMLeaderBackgroundMask выше). Здесь коллизии не возникает:
; (assoc 304 ...) берёт ПЕРВОЕ вхождение в списке - а это и есть
; настоящий текст (он идёт в записи РАНЬШЕ маркера "LEADER_LINE{"),
; подтверждено дампом entget на реальном объекте.
;=====================================================================

(defun LEP:AppendMLeaderText (LabelEnt ExtraText)

    (LEP:SetMLeaderText
        LabelEnt
        (strcat (LEP:GetMLeaderText LabelEnt) "\\P" ExtraText)
    )

)


;=====================================================================
; LEP:GetMLeaderText / LEP:SetMLeaderText
;
; Прочитать / заменить ЦЕЛИКОМ текст готовой выноски MLEADER. Вынесено
; из LEP:AppendMLeaderText (2026-07-28), когда понадобилось не
; дописать строку, а перенести текст подписи со старой опоры на новую
; (C:LEP-POLE-MOVE, LEP-POLE.LSP) - чтобы работа с группой 304 (со
; всеми её ловушками, описанными выше) осталась в ОДНОМ месте проекта,
; а не расползлась по модулям двумя почти одинаковыми кусками.
;
; Про (assoc 304 ...) и второе, служебное вхождение той же группы
; глубже в записи MULTILEADER - см. подробный разбор в шапке
; LEP:AppendMLeaderText: берётся ПЕРВОЕ вхождение, а это и есть
; настоящий текст (подтверждено живым тестом 2026-07-15).
;=====================================================================

(defun LEP:GetMLeaderText (LabelEnt)

    (cdr (assoc 304 (entget LabelEnt)))

)


(defun LEP:SetMLeaderText (LabelEnt NewText / D)

    (setq D (entget LabelEnt))
    (setq D (subst (cons 304 NewText) (assoc 304 D) D))
    (entmod D)
    (command "_.REGEN")

)



(princ "\nLEP-UTILS загружен.")

(princ)
