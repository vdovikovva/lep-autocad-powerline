;=====================================================================
;
;  ПРОЕКТ:      LEP (Автоматизация проектирования ЛЭП)
;
;  ФАЙЛ:        LEP-CONFIG.LSP
;
;  ВЕРСИЯ:      0.1
;
;  АВТОРЫ:      Пользователь + ChatGPT
;
;  НАЗНАЧЕНИЕ:
;
;  Данный файл содержит ВСЕ глобальные настройки проекта.
;
;  ВАЖНО!
;
;  Любые строки, числа, имена слоёв, размеры текста,
;  цвета, коэффициенты округления и прочие параметры
;  должны храниться ТОЛЬКО ЗДЕСЬ.
;
;  Остальные модули НЕ ДОЛЖНЫ содержать "магических"
;  чисел и строк.
;
;=====================================================================



;=====================================================================
;                           ВЕРСИЯ ПРОЕКТА
;=====================================================================
;
; Сквозная версия ВСЕГО проекта (печатается в баннере при загрузке
; CONFIG) - у отдельных модулей свои версии в шапках файлов. Поднята
; 0.1 -> 0.2 при аудите 2026-07-11 (висела с самого начала, хотя
; проект ушёл далеко вперёд).
;
;=====================================================================

(setq *LEP-Version* "0.2")



;=====================================================================
;                           НАСТРОЙКИ ПРОЕКТА
;=====================================================================

(setq *LEP-ProjectName* "LEP")



;=====================================================================
;                           СЛОИ
;=====================================================================

;; Подложка

(setq *LEP-Layer-Kadastr*       "LEP-KADASTR")


;; Служебная линия маршрута (LEP-ROUTE) - НЕ настоящий ВЛ/КЛ, просто
;; "арматура" для констрейнтов опор. Печать всегда выключена (см.
;; LEP-SETUP), видимость на экране переключается командой
;; LEP-ROUTEVIS, чтобы не перекрывать пунктир пролётов КЛ.

(setq *LEP-Layer-Route*         "LEP-ROUTE-SERVICE")


;; Воздушные линии
;;
;; ✅ ДОБАВЛЕНО 2026-07-22 (по просьбе пользователя - разный цвет по
;; классу напряжения, не только по статусу Проект/Сущ.): вместо ОДНОГО
;; слоя на статус - ЧЕТЫРЕ (класс x статус). *LEP-Layer-Proj-VL*/
;; *LEP-Layer-Exist-VL* СОЗНАТЕЛЬНО оставлены как константы, но
;; переопределены в составную строку "слой1,слой2" через запятую - тот
;; же приём, что и у *LEP-Layer-Proj-KL* чуть ниже (см. подробное
;; объяснение там же) - весь СУЩЕСТВУЮЩИЙ код, который сканирует ВЛ по
;; этим именам (LEP-REPORT.LSP, LEP-DATA.LSP LEP:ReassignRoute,
;; LEP-SPAN.LSP LEP:GetSpanNeighbors/FindGroupMembers), продолжает
;; работать БЕЗ единой правки - ssget с несколькими слоями через
;; запятую в одном фильтре уже умеет матчить "любой из списка".
;; Для СОЗДАНИЯ слоёв (LEP-SETUP.LSP) и для ВСТАВКИ нового объекта
;; (LEP-POLE.LSP/LEP-END.LSP/LEP-SPAN.LSP) используются granular
;; константы ниже, выбор среди них - по классу напряжения МАРШРУТА
;; (VCLASS в XDATA) в момент вставки.
(setq *LEP-Layer-Proj-VL-10*    "LEP-PROJ-VL-10")
(setq *LEP-Layer-Proj-VL-04*    "LEP-PROJ-VL-04")
(setq *LEP-Layer-Exist-VL-10*   "LEP-EXIST-VL-10")
(setq *LEP-Layer-Exist-VL-04*   "LEP-EXIST-VL-04")
(setq *LEP-Layer-Proj-VL*       (strcat *LEP-Layer-Proj-VL-10* "," *LEP-Layer-Proj-VL-04*))
(setq *LEP-Layer-Exist-VL*      (strcat *LEP-Layer-Exist-VL-10* "," *LEP-Layer-Exist-VL-04*))


;; Кабельные линии
;;
;; ✅ ДОБАВЛЕНО 2026-07-22 (по просьбе пользователя): у Проект. КЛ
;; теперь спрашивается способ прокладки (ГНБ/Траншея, LEP-SPAN.LSP) -
;; у каждого способа свой цвет (см. ниже), поэтому вместо ОДНОГО слоя
;; Проект. КЛ - два granular слоя. Сущ. КЛ способом прокладки не
;; различается (не спрашивается) - остаётся один слой, без изменений.
;;
;; ⚠️ *LEP-Layer-Proj-KL* СОЗНАТЕЛЬНО оставлен существующей константой,
;; но переопределён в СПИСОК ИЗ ДВУХ ИМЁН ЧЕРЕЗ ЗАПЯТУЮ, а не удалён -
;; весь остальной код проекта (LEP-DATA.LSP LEP:ReassignRoute,
;; LEP-REPORT.LSP сканирование ведомости, LEP-SPAN.LSP поиск соседних
;; пролётов) уже использует этот приём "несколько слоёв через запятую
;; в одном фильтре ssget" (see LEP:ReassignRoute) - подставив сюда
;; строку с запятой ВМЕСТО одного имени, весь ЭТОТ существующий код
;; продолжает работать НЕ МЕНЯЯСЬ ВООБЩЕ (ssget с фильтром по слою и
;; так принимает список через запятую как ИЛИ). Только НЕ подходит для
;; создания нового слоя (LEP:CreateLayer с этой строкой создал бы ОДИН
;; слой с запятой в имени, что неверно) - поэтому для СОЗДАНИЯ слоёв в
;; LEP-SETUP.LSP используются НОВЫЕ granular константы ниже, а для
;; ВСТАВКИ нового пролёта в LEP-SPAN.LSP - тоже они (LayerName
;; выбирается явно по способу прокладки, не через этот составной
;; список).
(setq *LEP-Layer-Proj-KL-GNB*      "LEP-PROJ-KL-GNB")
(setq *LEP-Layer-Proj-KL-Trench*   "LEP-PROJ-KL-TRENCH")
(setq *LEP-Layer-Proj-KL*          (strcat *LEP-Layer-Proj-KL-GNB* "," *LEP-Layer-Proj-KL-Trench*))
(setq *LEP-Layer-Exist-KL*      "LEP-EXIST-KL")


;; Опоры
;;
;; ✅ ДОБАВЛЕНО 2026-07-22: та же логика "класс x статус", что и у ВЛ
;; выше (см. подробное объяснение там же - составная строка через
;; запятую для обратной совместимости сканирующего кода).
(setq *LEP-Layer-Proj-Pole-10*  "LEP-PROJ-POLE-10")
(setq *LEP-Layer-Proj-Pole-04*  "LEP-PROJ-POLE-04")
(setq *LEP-Layer-Exist-Pole-10* "LEP-EXIST-POLE-10")
(setq *LEP-Layer-Exist-Pole-04* "LEP-EXIST-POLE-04")
(setq *LEP-Layer-Proj-Pole*     (strcat *LEP-Layer-Proj-Pole-10* "," *LEP-Layer-Proj-Pole-04*))
(setq *LEP-Layer-Exist-Pole*    (strcat *LEP-Layer-Exist-Pole-10* "," *LEP-Layer-Exist-Pole-04*))


;; Подстанции

(setq *LEP-Layer-Proj-MTP*      "LEP-PROJ-MTP")
(setq *LEP-Layer-Proj-RLK*      "LEP-PROJ-RLK")
(setq *LEP-Layer-Exist-TP*      "LEP-EXIST-TP")
(setq *LEP-Layer-Proj-TP*       "LEP-PROJ-TP")


;; Текст

(setq *LEP-Layer-Text*          "LEP-TEXT")
(setq *LEP-LeaderOffset* 5.0)   ; метров (после калибровки 1 ед. = 1 м), можно потом подвинуть под глаз


;; Размеры

(setq *LEP-Layer-Dim*           "LEP-DIM")


;; Служебный слой "для ручного черчения" - создаётся ПОСЛЕДНИМ в
;; LEP-SETUP.LSP (см. C:LEP-SETUP). Смысл: команда "-LAYER Make" в
;; AutoCAD всегда делает только что созданный слой ТЕКУЩИМ (это
;; поведение самой команды, не наш баг - уже ловили из-за этого баг
;; с подложкой, попадавшей не на тот слой в LEP-SCALE). Раз это
;; неизбежно, пусть текущим после автозапуска LEP-SETUP (см.
;; LEP-START.LSP) остаётся НЕ технический слой (было бы плохо - любая
;; случайная линия "мимо команды" попадёт в ВЛ/КЛ/опоры и испортит
;; ведомость), а специально отведённый под ручные пометки/черновые
;; построения. Пользователь всегда может переключиться на нужный слой
;; сам - это просто безопасный дефолт.

(setq *LEP-Layer-Manual*        "LEP-MANUAL")



;=====================================================================
;                           ЦВЕТА СЛОЁВ
;=====================================================================
;
; Используются стандартные ACI цвета AutoCAD.
;
; При необходимости можно изменить здесь, не меняя код.
;
;=====================================================================

(setq *LEP-Color-Proj*          1)      ; Красный (в т.ч. служебная линия маршрута)
(setq *LEP-Color-Exist*         8)      ; Серый
(setq *LEP-Color-Text*          7)      ; Белый
(setq *LEP-Color-Dim*           7)      ; Белый
(setq *LEP-Color-Manual*        7)      ; Белый - нейтральный, не пересекается с проектными цветами
(setq *LEP-Color-Kadastr*       9)

;; ВЛ и КЛ разнесены по цвету отдельно от *LEP-Color-Proj* - удобнее
;; отличать на глаз при проектировании. Временные, пользователь сам
;; поправит после согласования с коллегой.
(setq *LEP-Color-Proj-VL*       30)     ; Оранжевый
(setq *LEP-Color-Proj-KL*       5)      ; Синий (⚠️ УСТАРЕЛО - Проект. КЛ
                                         ; больше не рисуется этим цветом
                                         ; напрямую, см. ГНБ/Траншея ниже;
                                         ; оставлено на случай, если
                                         ; где-то ещё используется как
                                         ; запасное значение)

;; ✅ ДОБАВЛЕНО 2026-07-22 (по просьбе пользователя, цвета сняты с
;; экрана AutoCAD - True Color/RGB, НЕ обычный номер ACI 1-255, как
;; всё остальное в этом файле). ✅ True Color ПОДТВЕРЖДЁН ЖИВЫМ ТЕСТОМ
;; 2026-07-22 (пользователь создал тестовый слой через entmod DXF-
;; группы 420 - диспетчер слоёв AutoCAD показал реальный фиолетовый
;; цвет) - см. LEP:SetLayerTrueColor в LEP-SETUP.LSP, вызывается там
;; сразу после LEP:CreateLayer для каждого из 4 слоёв ниже, чтобы
;; переопределить временный ACI-цвет (`Placeholder`) настоящим RGB.
;; `Placeholder`-константы остаются НУЖНЫ - LEP:CreateLayer всё ещё
;; требует какой-то ACI-номер как ПЕРВОНАЧАЛЬНЫЙ цвет при самом
;; создании слоя (`-LAYER Make ... Color N`), просто он тут же
;; перезаписывается настоящим RGB следующей строкой.
(setq *LEP-TrueColor-Proj-KL-GNB*      (list 16 86 137))   ; R G B
(setq *LEP-TrueColor-Proj-KL-Trench*   (list 69 84 165))   ; R G B
(setq *LEP-Color-Proj-KL-GNB-Placeholder*    5)  ; ACI - начальный цвет при создании, тут же заменяется True Color
(setq *LEP-Color-Proj-KL-Trench-Placeholder* 5)  ; ACI - начальный цвет при создании, тут же заменяется True Color

;; Опоры/ВЛ по классу напряжения x статус (тоже 2026-07-22, по просьбе
;; пользователя): 10кВ Сущ - красный и 0,4кВ Проект - синий - ОБЫЧНЫЕ
;; ACI-цвета (не True Color), никакого дополнительного шага не нужно.
;; 0,4кВ Сущ - True Color (см. ✅ выше про КЛ - тот же подтверждённый
;; механизм).
(setq *LEP-Color-Exist-VL-10*   1)   ; Красный (ACI)
(setq *LEP-Color-Proj-VL-04*    5)   ; Синий (ACI)
(setq *LEP-TrueColor-Exist-VL-04* (list 147 39 143))  ; R G B
(setq *LEP-Color-Exist-VL-04-Placeholder* 6)          ; ACI - начальный цвет при создании, тут же заменяется True Color



;=====================================================================
;                  ТЕКСТОВЫЙ СТИЛЬ (LEP-SETUP.LSP)
;=====================================================================
;
; Единый текстовый стиль для ВСЕХ надписей проекта (подписи опор,
; пролётов, маршрута, размерная линия) - по просьбе пользователя
; 2026-07-10, наклонный ISOCPEUR, высота 1,3 (как в присланных
; референс-чертежах, тоже масштаб 1:1).
;
; ВАЖНО: "ISOCPEUR" (БЕЗ расширения ".shx"!) - штатный шрифт AutoCAD,
; но на проверенной установке это TrueType-шрифт (иконка "TT" в
; диалоге "Текстовые стили"), а не SHX-файл, как можно было бы
; подумать по имени - живьём сверено с пользователем. Если когда-то
; понадобится классический SHX с похожим видом - есть "isocp.shx"
; (без "eur", тоже штатный, точно SHX). Никакой отдельный файл в папку
; проекта добавлять не нужно - шрифт уже есть в самом AutoCAD. Стиль
; создаётся кодом
; (entmake на таблицу STYLE) - то же самое, что выбрать этот шрифт
; мышкой в диалоге "Текстовые стили".
;
; Высота (*LEP-TextHeight*) задаётся ФИКСИРОВАННОЙ в самом стиле (не 0) -
; это не только высота обычного текста/подписей, но и ОДНОВременно
; высота текста размерных линий (DIMALIGNED): в AutoCAD, если у
; текстового стиля, назначенного размерному стилю (DIMTXSTY), высота
; задана явно (не 0) - она ЗАМЕЩАЕТ DIMTXT, отдельно эту переменную
; трогать не нужно (задокументированное поведение AutoCAD).
;
; Угол наклона (*LEP-TextStyle-ObliqueAngle*) хранится здесь в
; ГРАДУСАХ (удобнее человеку читать/менять число) - перевод в радианы
; для группы DXF 50 у таблицы STYLE происходит в LEP-SETUP.LSP
; (LEP:CreateTextStyle) непосредственно перед entmake. ⚠️ Проверено
; вживую в консоли 2026-07-10: изначально предполагал, что у STYLE
; угол в градусах (единственное исключение в проекте) - оказалось
; неверно, DXF хранит радианы, как и везде остальное - диалог
; AutoCAD просто ПОКАЗЫВАЕТ пользователю градусы, но внутри
; конвертирует. Без перевода в радианы наклон текста визуально не
; появлялся вообще (число "10" как радианы - это ~573°, AutoCAD тихо
; сбрасывал такой угол).
;
;=====================================================================

(setq *LEP-TextStyle-Name*          "LEP-STYLE")
(setq *LEP-TextStyle-Font*          "ISOCPEUR")
(setq *LEP-TextStyle-ObliqueAngle*  10)     ; градусы (перевод в радианы - в LEP-SETUP.LSP)
(setq *LEP-TextHeight*              1.3)   ; м



;=====================================================================
;         РАЗМЕР СТРЕЛКИ / ДЛИНА ПОЛКИ ВЫНОСОК (LEP-SETUP.LSP)
;=====================================================================
;
; ✅ НАЙДЕННАЯ ПРИЧИНА "отступа перед текстом" у подписей-выносок
; (LEADER), которую долго не могли вылечить (полная история попыток -
; в LEP-README.md): полка (hookline), которую LEADER сам пристраивает
; после наклонного сегмента выноски, имеет длину, равную РАЗМЕРУ
; СТРЕЛКИ - системная переменная DIMASZ. У метрического размерного
; стиля ISO-25 по умолчанию DIMASZ = 2.5, а в нашем масштабе
; (1 ед. = 1 м) это 2,5 МЕТРА полки между изломом выноски и началом
; текста. Именно поэтому DIMGAP = 0 и смена шрифта ничего не давали -
; крутили не ту ручку. Подтверждено живым тестом в консоли 2026-07-11:
; DIMASZ 0.8 -> полка сжалась втрое; пользователь сравнил оба варианта
; на реальном объекте и выбрал мелкий.
;
; ("На винде такого гемора не было" - потому что там обычно чертят в
; МИЛЛИМЕТРАХ: та же полка 2.5 при 1 ед. = 1 мм - это 2,5 мм на бумаге,
; глазом не заметить. У нас 1 ед. = 1 МЕТР, и то же самое число
; превращается в громадину рядом с опорой размером 1 м. Дело не в
; Windows против Mac, а в масштабе единиц чертежа.)
;
; ВНИМАНИЕ: DIMASZ - размер стрелок ВСЕХ размерных объектов сразу,
; включая размерные линии пролётов (DIMALIGNED в LEP-SPAN) - у них
; стрелки тоже станут мелкими. Это сознательное решение пользователя
; ("меняй все под него").
;
;=====================================================================

(setq *LEP-Dim-ArrowSize*       0.8)    ; м; дефолт ISO-25 был 2.5

;; Форма стрелки (First/Second/Leader в диалоге "Symbols and Arrows") -
;; "Oblique" (косая черта), а не дефолтная закрашенная стрелка - по
;; просьбе пользователя 2026-07-15. "_OBLIQUE" - зарезервированное имя
;; AutoCAD для этого варианта (не имя блока в чертеже - служебный
;; идентификатор, распознаётся системными переменными DIMBLK1/DIMBLK2/
;; DIMLDRBLK напрямую, штатное поведение AutoCAD, не наш формат).
(setq *LEP-Dim-ArrowBlock*      "_OBLIQUE")



;=====================================================================
;    ОРИЕНТАЦИЯ ТЕКСТА РАЗМЕРНОЙ ЛИНИИ ПРОЛЁТА (LEP-SETUP.LSP)
;=====================================================================
;
; ⚠️ ИСПРАВЛЕНО 2026-07-15 (по жалобе пользователя): текст расстояния
; у DIMALIGNED (LEP:CreateSpanDimension, LEP-SPAN.LSP) всегда рисовался
; ГОРИЗОНТАЛЬНО ("смотрит вверх"), независимо от угла самого пролёта -
; хотя в старом комментарии в LEP-SPAN.LSP было написано "поворачивается
; вместе с линией" - это оказалось НЕ проверено вживую и было неверно
; (см. LEP-README.md). Причина - у AutoCAD (любой дефолтный DIMSTYLE,
; в т.ч. ISO-25) по умолчанию DIMTIH/DIMTOH = 1 (текст ВСЕГДА
; горизонтален, и внутри, и снаружи выносных линий) - этот проект
; никогда явно не выставлял их в 0.
;
; *LEP-Dim-TextInsideHorizontal*/*LEP-Dim-TextOutsideHorizontal* = 0 -
; текст поворачивается ВМЕСТЕ с размерной линией (совпадает с углом
; пролёта). Это ШТАТНОЕ, надёжное поведение AutoCAD - при развороте на
; 180° (линия "смотрит" в обратную сторону) AutoCAD сам выбирает
; читаемое направление текста, не переворачивает его вверх ногами -
; это штатная, документированная логика простановки размеров, не наша
; самодельная геометрия (для сравнения: у типа линии со встроенным
; текстом такой "умной" логики нет вообще - именно поэтому кабельная
; линия со штампом "K" была убрана из проекта 2026-07-15, см.
; отдельный раздел ниже).
;
; *LEP-Dim-TextAbove* = 1 (DIMTAD) - текст НАД размерной линией целиком
; (не разрывает её посередине, как при DIMTAD=0/Centered) - по прямой
; просьбе пользователя ("должен быть... над ней").
;
; ✅ ДОБАВЛЕНО 2026-08-04 (аудит по просьбе пользователя "проверь,
; чтобы у ВСЕХ подписей стоял background mask и draworder front"):
; *LEP-Dim-TextFill* = 1 (DIMTFILL) - ФОН ПОД ТЕКСТОМ РАЗМЕРА.
;
; Это была настоящая дырка. У всех выносок MLEADER (опоры, маршрут,
; пролёт, КТП, киоск) фон под текстом ставится с 2026-07-15
; (LEP:SetMLeaderBackgroundMask), а у размерных линий пролёта - НЕ
; ставился вообще: DIMTFILL нигде не выставлялся, держался дефолт
; AutoCAD (0 = фона нет). На чистом холсте это незаметно, а поверх
; геодезической подосновы, где под размером проходят линии рельефа,
; заборы и контуры зданий, число становится нечитаемым. DIMTAD=1
; (текст над линией) спасает только от СВОЕЙ размерной линии, от
; подосновы - нет.
;
; Значения DIMTFILL: 0 = без фона, 1 = цвет фона чертежа, 2 = цвет из
; DIMTFILLCLR. Берём 1 - ровно то же самое, что стоит у выносок
; MLEADER (там пользователь включил маску галочкой "использовать цвет
; фона чертежа", см. раздел про фоновую маску ниже).
;
; ⚠️ Как и у выносок, при ПЕЧАТИ на белом листе поведение "цвета фона
; чертежа" вживую не проверялось - только на экране (тёмный холст).
; Если на печати вокруг числа окажется тёмный прямоугольник - тут же и
; чинить: поставить 2 и задать DIMTFILLCLR явным белым.
;
;=====================================================================

(setq *LEP-Dim-TextInsideHorizontal*  0)    ; DIMTIH; 0 = поворачивается вместе с линией (было 1 - всегда горизонтально)
(setq *LEP-Dim-TextOutsideHorizontal* 0)    ; DIMTOH; 0 = поворачивается вместе с линией (было 1 - всегда горизонтально)
(setq *LEP-Dim-TextAbove*             1)    ; DIMTAD; 1 = текст над линией целиком, не разрывает её
(setq *LEP-Dim-TextFill*              1)    ; DIMTFILL; 1 = фон под текстом цветом фона чертежа (0 = без фона, дефолт AutoCAD)



;=====================================================================
;         СТИЛЬ ВЫНОСОК MLEADER (LEP-SETUP.LSP / LEP-POLE.LSP /
;              LEP-ROUTE.LSP / LEP-SPAN.LSP) - миграция с LEADER
;=====================================================================
;
; Начиная с 2026-07-15 подписи-выноски (опоры/маршрута/пролёта)
; создаются через MLEADER, а не через классический LEADER. Причина:
; у MLEADER стрелка+полка+текст - ОДИН объект (двигаются вместе при
; редактировании), плюс можно закрепить "текст лежит НА полке,
; подчёркнутый" (как в реальных чертежах коллеги пользователя) прямо
; в стиле - у LEADER так не получалось в принципе (полка и текст были
; двумя независимыми сущностями с собственной, не всегда предсказуемой,
; геометрией - вся история мытарств с "отступом перед текстом" выше по
; файлу как раз из-за этого).
;
; ⚠️ ВАЖНО: MLEADERSTYLE - это НЕ классическая именная таблица AutoCAD
; (LAYER/STYLE/DIMSTYLE и т.п.), а объект внутри именованного словаря
; (namedobjdict -> ACAD_MLEADERSTYLE -> "Standard"). tblsearch/tblobjname
; для него возвращают nil - искать через dictsearch (см.
; LEP:CreateMLeaderStyle в LEP-SETUP.LSP). Это уже один раз поймали
; вживую (entmod падал с "bad argument type: lentityp nil").
;
; Настраивается НАПРЯМУЮ стиль "Standard" (тот же, что AutoCAD
; использует по умолчанию для любого MLEADER), а не отдельный
; LEP-именной стиль - сознательно, по аналогии с *LEP-Dim-ArrowSize*
; (там тоже правится глобальная системная переменная DIMASZ, а не
; отдельный DIMSTYLE). Создать полноценный отдельный MLEADERSTYLE
; через entmake "с нуля" не пробовали живьём (в отличие от STYLE/LAYER,
; для которых уже подобрана рабочая структура) - according to правилу
; проекта "не гадать, а тестировать" это отдельная, непроверенная
; задача, пока не нужна. Побочный эффект (сознательный, как и с
; DIMASZ): ЛЮБОЙ MLEADER в чертеже, включая созданный пользователем
; вручную мышкой, получит эти же настройки.
;
; Значения ниже НАЙДЕНЫ ЖИВЫМ ТЕСТОМ в консоли (entget/subst/entmod по
; одной группе DXF за раз в чистом новом чертеже, 2026-07-15) -
; НЕ из памяти/документации:
;
;   43 (LandingDistance) - длина полки. Дефолт AutoCAD 8.0 - в нашем
;       масштабе (1 ед.=1м) это 8-метровая полка, аналогично истории
;       с DIMASZ. Изолированный тест подтвердил: меняет ТОЛЬКО длину
;       полки.
;   44 (ArrowSize) - размер стрелки на конце выноски. Дефолт 4.0 -
;       тоже гигантский в нашем масштабе. ⚠️ Была ошибочная гипотеза,
;       что это высота текста - опровергнута пользователем на
;       реальном тесте (текст не менялся, менялась только стрелка).
;   45 (TextHeight) - высота текста. Дефолт 4.0. Подтверждено
;       изолированным тестом (43 и 44 на дефолте, менялась только 45 -
;       поменялся только размер букв). Специально НЕ хранится тут
;       отдельным числом - берётся *LEP-TextHeight* (тот же параметр,
;       что и у обычного текстового стиля LEP-STYLE) при вызове
;       LEP:CreateMLeaderStyle, чтобы высота текста была одна и та же
;       величина везде по проекту, а не два разных числа, которые
;       кто-то забудет поменять синхронно.
;   42 (LandingGap) - зазор между полкой и текстом. Дефолт 2.0 м -
;       тоже многовато. Пользователь вручную поставил 0 в диалоге
;       "Multileader Style Manager" и это ему понравилось - берём то
;       же значение.
;   93 (TextColor) - цвет текста, RAW DXF-значение (не обычный номер
;       ACI!). Пользователь поставил в диалоге "ByLayer" - получившееся
;       число -1073741824 подтверждено ДО/ПОСЛЕ дампом dictsearch
;       (см. историю чата 2026-07-15). Копировать это число в другой
;       смысл (например, как обычный код цвета 1-255) НЕЛЬЗЯ - это
;       именно битовая ByLayer-метка для данного конкретного
;       DXF-поля.
;   174/178 (TextAttachmentType, левая/правая сторона) и 295/298
;       (флаги подчёркивания) - ⚠️ НЕ проверены ПО ОТДЕЛЬНОСТИ (какая
;       именно из четвёрки отвечает за что) - но КОМБИНАЦИЯ целиком
;       эмпирическая: это ровно то, что сам AutoCAD записал в
;       DXF-запись стиля после того, как пользователь включил галочку
;       "Underline bottom line" (для обоих вариантов - слева и справа)
;       в реальном диалоге настройки стиля и получил желаемую картинку
;       "текст лежит на полке, подчёркнутый". Не гадание из головы -
;       живой факт, снятый через тот же dictsearch-дамп. Если понадобится
;       разобраться, какая группа что делает по отдельности - см.
;       LEP-README.md, это отложено как неприоритетное уточнение.
;   342 (TextStyleHandle) - хендл текстового стиля контента выноски.
;       ⚠️ ПОДТВЕРЖДЕНО живым тестом 2026-07-15 (чистый И боевой
;       чертёж): по умолчанию у "Standard" смотрит на дефолтный
;       текстовый стиль AutoCAD (без наклона) - поэтому подписи через
;       MLEADER рисовались БЕЗ наклона 10°/шрифта ISOCPEUR, хотя весь
;       остальной текст на чертеже - с ними. НЕ хранится тут числом
;       (хендл специфичен для конкретного чертежа, копировать между
;       чертежами литералом бессмысленно) - вычисляется заново в
;       LEP:CreateMLeaderStyle (LEP-SETUP.LSP) через
;       (tblobjname "STYLE" *LEP-TextStyle-Name*) при каждой загрузке.
;
; НЕ ТРОГАТЬ при настройке стиля (важно, если код тут будут
; когда-нибудь менять): группа 300 (дефолтный текст стиля - в диалоге
; пользователя туда во время теста попал мусор "Тестовый\PТекст", это
; НЕ настройка, а случайный побочный эффект теста), 340/341/343
; (хендлы на другие объекты чертежа - типы линий/блок стрелки -
; копировать как литеральное число между разными чертежами
; бессмысленно и опасно, в отличие от 342 выше - тот вычисляется
; заново, а не копируется), 90 (внутренний битовый флаг AutoCAD "что
; переопределено", им не рулят вручную).
;
;=====================================================================

(setq *LEP-MLeader-LandingDistance*   1.0)    ; м; группа 43, дефолт был 8.0
(setq *LEP-MLeader-LandingGap*        0.0)    ; м; группа 42, дефолт был 2.0
(setq *LEP-MLeader-ArrowSize*         0.8)    ; м; группа 44, дефолт был 4.0 (визуально согласовано с *LEP-Dim-ArrowSize* - можно подправить по месту после проверки на реальном чертеже, живым тестом проверялось значение 1.0)
(setq *LEP-MLeader-TextColorValue*    -1073741824) ; группа 93, RAW DXF - ByLayer (см. пояснение выше, НЕ обычный код цвета)
(setq *LEP-MLeader-AttachLeft*        5)      ; группа 174, дефолт был 1
(setq *LEP-MLeader-AttachRight*       5)      ; группа 178, дефолт был 1
(setq *LEP-MLeader-Underline1*        1)      ; группа 295, дефолт был 0
(setq *LEP-MLeader-Underline2*        1)      ; группа 298, дефолт был 0



;=====================================================================
;    ФОНОВАЯ МАСКА ТЕКСТА ВЫНОСОК (LEP-UTILS.LSP / MLEADER) - ⚠️ ЭТО
;         НЕ СВОЙСТВО СТИЛЯ, СВОЙСТВО КАЖДОЙ ОТДЕЛЬНОЙ ВЫНОСКИ
;=====================================================================
;
; По просьбе пользователя 2026-07-15: фон под текстом подписей/выносок,
; чтобы линии чертежа, попадающие под текст, не просвечивали и не
; мешали читать.
;
; ⚠️ ВАЖНОЕ ОТЛИЧИЕ от остальных настроек MLEADER выше: фоновая маска -
; НЕ поле стиля MLEADERSTYLE (проверено - независимая библиотека ezdxf
; перечисляет ВСЕ поля объекта MLeaderStyle, ничего похожего на
; "background"/"mask" там нет). Это поле блока CONTEXT_DATA внутри
; КАЖДОЙ ОТДЕЛЬНО СОЗДАННОЙ выноски (сущность MULTILEADER) - то есть
; настроить один раз на весь чертёж, как полку/стрелку/наклон текста
; (LEP:CreateMLeaderStyle), НЕЛЬЗЯ. Приходится выставлять на КАЖДОЙ
; выноске сразу после её создания - LEP:SetMLeaderBackgroundMask
; (LEP-UTILS.LSP), тот же принцип, что и у LEP:SetEntityLWeight для
; символа опоры (свойство самого вставленного объекта, не блока).
;
; ⚠️ Найдено живым тестом (2026-07-15, реальная выноска на боевом
; чертеже, entget/subst/entmod - не из головы): группы 291
; (has_text_bg_color), 292 (has_text_bg_fill), 91 (RAW-цвет фона),
; 141 (масштаб рамки фона, дефолт AutoCAD при первом включении - 1.5).
; ⚠️ 92 (прозрачность фона) НЕ трогаем - пользователь её не менял в
; тесте, оставляем как есть (непрозрачный фон).
;
; ⚠️⚠️ КРИТИЧНО ПРИ ПРАВКЕ КОДА: в отличие от MLEADERSTYLE (там каждая
; группа встречается в записи РОВНО ОДИН РАЗ), у самой сущности
; MULTILEADER структура ВЛОЖЕННАЯ (CONTEXT_DATA{ -> LEADER{ ->
; LEADER_LINE{) и коды ПОВТОРЯЮТСЯ - например (292 . 0) реально
; встречается в записи ДВАЖДЫ (наше поле фона + не связанное с ним
; поле где-то внутри LEADER{, судя по именам полей ezdxf - параметр
; блочного контента, у нас не используется, т.к. контент выноски -
; текст, не блок). Обычный (assoc)+(subst) заменяет ВСЕ вхождения с
; одинаковым значением - живым тестом поймано, что "слепой" subst
; ошибочно перезаписывает и это второе, чужое поле тоже. Поэтому
; LEP:SetMLeaderBackgroundMask правит ТОЛЬКО "голову" списка - часть
; ДО первого маркера (302 . "LEADER{") - хвост (сам LEADER{ со всей
; вложенностью) вообще не трогается, коллизия невозможна по построению.
;
; ⚠️ RAW-значение цвета (-1027028792) - то, что AutoCAD сам записал,
; когда пользователь включил маску БЕЗ выбора конкретного цвета
; (галочка "Использовать цвет фона чертежа" по умолчанию) - НЕ
; декодировано побитово, что именно оно означает визуально при печати
; (белый лист) - не проверено, только на экране (чёрный холст). Если
; при печати фон будет выглядеть не так, как ожидается - see запись в
; README, нужно будет подобрать другое значение живым тестом (выбрать
; конкретный цвет в диалоге, не "по умолчанию").
;
;=====================================================================

(setq *LEP-MLeader-BgColorValue*      -1027028792) ; группа 91, RAW DXF - "цвет фона чертежа" (см. пояснение выше, не декодировано побитово)
(setq *LEP-MLeader-BgScale*           1.5)         ; группа 141, дефолт AutoCAD при включении маски



;=====================================================================
;                     ТИПЫ ЛИНИЙ ПРОЛЁТОВ (LEP-SPAN)
;=====================================================================
;
; ⚠️ УБРАНО 2026-07-15 (по прямой просьбе пользователя, "задолбало"):
; раньше КЛ рисовалась своим типом линии со штампом "K" (файл
; LEP-LINETYPES.LIN, тип LEP_CABLE) - после серии живых тестов
; (поворот буквы A=/R=, размер буквы, разрыв вокруг неё) пользователь
; решил, что игра не стоит свеч, и попросил убрать эту линию совсем.
; Теперь ВЛ и КЛ рисуются ОДИНАКОВО - обе сплошной линией
; ("CONTINUOUS", всегда есть в AutoCAD), отличаются друг от друга
; только слоем/цветом (*LEP-Layer-Proj-VL*/*LEP-Layer-Proj-KL*,
; оранжевый/синий) - см. LEP:CreateSpanEntity в LEP-SPAN.LSP.
; LEP-LINETYPES.LIN удалён из проекта целиком (см. историю git, если
; когда-нибудь понадобится восстановить).
;
;=====================================================================



;=====================================================================
;              ЗАПАС ДЛИНЫ ПРОВОДА/КАБЕЛЯ (LEP-SPAN)
;=====================================================================
;
; Расстояние между опорами (по прямой) и реальная длина провода/кабеля,
; которую нужно закупить/проложить - РАЗНЫЕ величины:
;
; ВЛ (провод) - провод провисает между опорами (стрела провеса), из-за
; этого реальной длины нужно чуть больше, чем прямое расстояние.
; *LEP-Sag-VL* - процент запаса.
;
; КЛ (кабель) - кабель в земле НЕ провисает (лежит в траншее), но у
; каждого конца пролёта есть концевая заделка, которой нужна слабина -
; это фиксированная добавка в метрах, не проценты. Считается ПОКОНЦОВО
; и зависит от того, что на конце стоит: у опоры кабель реально лезет
; наверх (*LEP-KL-Reserve-Pole*), у наземной КТП/киоска - нет
; (*LEP-KL-Reserve-Ground*). Подробности - ниже, у самих констант.
;
; Запас на муфты/разделку кабеля (ГОСТ/нормы прокладки в траншее) -
; СОЗНАТЕЛЬНО не считаем здесь, это остаётся на усмотрение
; проектировщика при подготовке настоящей сметы, программа даёт только
; черновую прикидку.
;
; ✅ ОБНОВЛЕНО 2026-07-24 (новые нормы запаса от пользователя):
;
;   1. Процент запаса ВЛ поднят с 2% до 4,5%.
;
;   2. У КЛ появился СВОЙ процент, РАЗНЫЙ для двух способов прокладки
;      (ГНБ 2% / траншея 4%) - и он идёт ПОВЕРХ метров на концевые
;      заделки, а не вместо них. Это НЕ дублирование запаса: метры -
;      реальная физическая длина кабеля у концов пролёта (уточнено
;      пользователем ещё 2026-07-22), а процент - запас на укладку
;      "змейкой"/неровности трассы. Разные величины, поэтому
;      складываются: (сырая длина + метры концов) x (1 + процент/100).
;      ⚠️ Эти проценты НЕ видны на чертеже - подпись КЛ показывает
;      только "сырая длина + 6 м", то есть чистую физику (прямое
;      указание пользователя 2026-07-24: "все запасы идут только в
;      ведомость"). За это отвечает ОТДЕЛЬНАЯ функция
;      LEP:GetDisplayLength в LEP-SPAN.LSP - не путать с
;      LEP:GetRealLength, которая считает длину для закупки.
;
;   3. Провод высокого напряжения (10 кВ и 6 кВ) умножается на 3 -
;      это НЕ запас, а число фаз: там СИП-3, у которого на каждую
;      фазу идёт ОТДЕЛЬНЫЙ провод, то есть на один пролёт надо три
;      длины. У 0,4 кВ провод СИП-2 - все жилы уже собраны в один
;      жгут, множитель 1. Множитель применяется ПОСЛЕ процента запаса
;      (прямая формулировка пользователя: "умножаем на 3 после
;      прибавления запасиков"), округление вверх до метра - ОДИН раз
;      в самом конце, после умножения.
;      ⚠️ Множитель НЕ применяется к КЛ даже на 10 кВ: кабель 10 кВ
;      трёхжильный, это одна строительная длина, а не три.
;
;=====================================================================

(setq *LEP-Sag-VL*              4.5)    ; % запаса на провис ВЛ
(setq *LEP-Sag-KL-GNB*          2)      ; % запаса КЛ, проложенной ГНБ (в трубе)
(setq *LEP-Sag-KL-Trench*       4)      ; % запаса КЛ, проложенной в траншее

;;--------------------------------------------------------------------
;; ПОРОГ ОКРУГЛЕНИЯ ДЛИН - ЕДИНОЕ ПРАВИЛО НА ВЕСЬ ПРОЕКТ
;;
;; ✅ ДОБАВЛЕНО 2026-08-05. До этого дня в программе жили ДВА разных
;; правила округления одной и той же величины, и пользователь поймал
;; это на живом чертеже: пролёт длиной 46,4958 м подписан выноской
;; "L=47 м" (округление ВВЕРХ, LEP:RoundUp), а размерная линия рядом,
;; на том же самом пролёте - "46 м" (по правилам математики,
;; LEP:RoundNearest). Два числа про одно и то же, отличаются на метр.
;;
;; Новое правило, прямое решение пользователя:
;;   длина БОЛЬШЕ порога -> округляем ВВЕРХ (запас материала важнее
;;                          красоты, вниз занижать нельзя);
;;   длина МЕНЬШЕ порога -> по обычным правилам математики.
;;
;; Зачем нижняя часть правила: на коротких величинах округление вверх
;; выглядит нелепо и врёт в разы - 1,1 м превратился бы в "2 м", это
;; почти двукратное завышение, и на чертеже читается как ошибка
;; черчения. На 46 метрах лишние полметра никто не заметит, на 1,1 м -
;; заметят сразу. Особенно это важно с 2026-08-04, когда у кабельной
;; траншеи появились размеры НА КАЖДОЕ КОЛЕНО (LEP:CreateSpanDimensions,
;; LEP-SPAN.LSP): колена бывают совсем короткие.
;;
;; ⚠️ На самом пороге разрыва НЕТ - специально проверено, потому что
;; пороговые правила часто его создают. 4.9 -> 5, ровно 5.0 -> 5,
;; 5.05 -> 5. Больший вход никогда не даёт меньший выход.
;;
;; ✅ ДОПОЛНЕНО 2026-08-11: *LEP-Round-UpTolerance*. Округление вверх
;; честно, но буквальный "потолок" срабатывает и на мусорном хвосте:
;; пользователь поймал размер Measurement = 50,0025 м, подписанный
;; "51 м". Два с половиной МИЛЛИМЕТРА, взявшихся из того, что точки
;; ставились мышкой, дали на чертеже лишний метр - и это читается как
;; ошибка, а не как запас. Поэтому перед потолком у длины отбрасывается
;; хвост НЕ БОЛЬШЕ допуска: 50,0025 -> 50 и 50,10 -> 50, но 50,11 -> 51.
;;
;; Допуск 10 см - решение пользователя. Смысл: это заведомо меньше
;; точности, с которой вообще ставится точка на подоснове, поэтому
;; отбрасываем мы не материал, а погрешность клика. Цена в ведомости -
;; максимум 10 см на позицию, против 1 м завышения на каждом пролёте,
;; где хвост оказался чуть больше нуля.
;;
;; ⚠️ Правило действует ВЕЗДЕ, включая ведомость (LEP:GetRealLength) -
;; это осознанно. Соблазн оставить в ведомости "всегда вверх" был, но
;; тогда мы бы починили одно расхождение и тут же завели второе:
;; выноска на чертеже "7 м", а строка CSV "8 м" на том же пролёте -
;; ровно то, из-за чего эта правка и делается. Цена: пролёт короче
;; порога может уйти в ведомости вниз, максимум на 0,5 м. Практически
;; это почти не встречается - до округления к сырой длине уже
;; прибавлены проценты запаса (у ВЛ 4,5%, у КЛ 2-4%), и они сами
;; перекидывают число через целое.
;;
;; Порог и допуск в метрах. Менять можно свободно - оба в одном месте и
;; используются единственной функцией LEP:RoundLength (LEP-UTILS.LSP).
;;--------------------------------------------------------------------

(setq *LEP-Round-UpThreshold*   5.0)    ; м, выше этого - округление вверх
(setq *LEP-Round-UpTolerance*   0.10)   ; м, хвост меньше этого не поднимает число вверх

;;--------------------------------------------------------------------
;; ЗАПАС КЛ НА КОНЦЕВЫЕ ЗАДЕЛКИ - СЧИТАЕТСЯ ПОКОНЦОВО
;;
;;⚠️ ПЕРЕДЕЛАНО 2026-08-03. Запас на подъем спуск = 0 м
;;⚠️ ПЕРЕДЕЛАНО 2026-07-24. Раньше была ОДНА константа
;; *LEP-KL-Reserve* = 6.0 м на весь пролёт ("по 3 м с каждой стороны
;; на подъём кабеля на опору"). Пока оба конца пролёта ВСЕГДА были
;; опорами, этого хватало. Но появился реальный случай (КТП -> два
;; кабеля 0,4 кВ -> кабельный киоск с двумя ПУ), где НИ ОДИН конец не
;; опора: из наземной подстанции кабель выходит внизу и в киоск заходит
;; внизу - лезть ему некуда, и жёсткие +6 м стали бы чистым
;; завышением на каждом таком пролёте.
;;
;; Теперь запас начисляется ЗА КАЖДЫЙ КОНЕЦ ОТДЕЛЬНО, по типу того,
;; что на этом конце стоит (LEP:GetEndReserve, LEP-SPAN.LSP):
;;   опора                -> *LEP-KL-Reserve-Pole*   (0 м, подъём)
;;   КТП / КК (наземное)  -> *LEP-KL-Reserve-Ground* (0 м, см. ниже)
;;
;; Отсюда: опора-опора = 6 м (как было, ничего не изменилось),
;; КТП-опора = 3 м, КТП-киоск = 0 м.
;;
;; ⚠️ *LEP-KL-Reserve-Ground* = 0 - это ОСОЗНАННЫЙ ноль, а не забытое
;; значение (прямое решение пользователя 2026-07-24: "пока запас 0, но
;; константу введи на будущее"). Константа заведена именно для того,
;; чтобы, когда понадобится закладывать слабину на разделку кабеля в
;; ячейке КТП или в киоске, это была правка ОДНОГО числа здесь, а не
;; поиск по коду. Ноль в формуле ничего не ломает - просто ничего не
;; добавляет.
;;
;; ⚠️ Посчитанный запас пишется в XDATA каждого пролёта (ключ RESERVE)
;; ПРИ СОЗДАНИИ - иначе общая подпись на группу пролётов не смогла бы
;; сложить запасы разных пролётов с разными концами. Смена констант
;; здесь, как и всегда, НЕ пересчитывает уже нарисованное.
;;--------------------------------------------------------------------

(setq *LEP-KL-Reserve-Pole*     0.0)    ; м, на ОДИН конец-опору (подъём по опоре)
(setq *LEP-KL-Reserve-Ground*   0.0)    ; м, на ОДИН наземный конец (КТП/КК)

;; Число фаз (= сколько отдельных проводов надо на один пролёт ВЛ) по
;; классу напряжения маршрута. Ключи - те же коды, что в
;; *LEP-VoltageClasses* ("10"/"6"/"04"), см. раздел про класс
;; напряжения выше в этом файле. Если появится новый класс - добавить
;; строку СЮДА, иначе LEP:GetPhaseCount (LEP-SPAN.LSP) молча посчитает
;; его в одну нитку.
(setq *LEP-Phases-ByClass*
    (list
        (cons "10" 3)
        (cons "6"  3)
        (cons "04" 1)
    )
)


;=====================================================================
;       ТРУБА ДЛЯ ГНБ-ПРОКОЛА (отдельная позиция ведомости)
;=====================================================================
;
; ✅ ДОБАВЛЕНО 2026-07-24 (новая позиция ведомости по просьбе
; пользователя). Когда кабель прокладывается ГНБ (горизонтально-
; направленным бурением, "проколом"), его тянут не прямо в грунте, а
; внутри пластиковых труб, которые сваривают/стыкуют из отрезков
; стандартной длины. Эти трубы - ОТДЕЛЬНЫЙ материал, который надо
; закупать штуками, поэтому в ведомости появляется своя строка -
; НЕЗАВИСИМО от метража самого кабеля.
;
; Формула (прямо со слов пользователя):
;   труб на прокол = ( округл_вверх( длина_прокола / 13 ) + 1 ) x 2
; где:
;   13    - *LEP-GNB-PipeLength*, длина одного отрезка трубы, м;
;   + 1   - *LEP-GNB-PipeSpare*, одна ЦЕЛАЯ труба запаса на прокол
;           (не процент - именно штука, на случай брака/подрезки);
;   x 2   - *LEP-GNB-PipesPerBore*, сколько труб идёт в одном проколе
;           (стандартно две - рабочая и резервная).
;
; ⚠️ Длина прокола берётся СЫРАЯ, "по плану" (RAWLENGTH в XDATA
; пролёта) - без процентов запаса на кабель: трубу кладут по факту
; трассы прокола, ей запас на укладку кабеля змейкой не нужен, свой
; запас у неё уже учтён отдельной трубой (+1 выше).
;
; ⚠️ ОДИН ПРОКОЛ - это СПЛОШНОЙ УЧАСТОК ГНБ, а не один пролёт между
; опорами (решение пользователя 2026-07-24). Если прокол под дорогой
; нарисован двумя-тремя пролётами подряд, это всё равно ОДИН прокол, и
; запасная труба добавляется на него ОДИН раз, а не на каждый пролёт.
; Как программа понимает, где кончается прокол - см. ЭТАП 1.7 в
; LEP-REPORT.LSP (группировка по общей подписи).
;
;=====================================================================

(setq *LEP-GNB-PipeLength*      13.0)   ; м, длина одного отрезка трубы
(setq *LEP-GNB-PipeSpare*       1)      ; шт., запасная труба на прокол
(setq *LEP-GNB-PipesPerBore*    2)      ; шт., труб в одном проколе

;; ✅ ДОБАВЛЕНО 2026-07-24: диаметр трубы - нужен ТОЛЬКО для третьей
;; строки подписи КЛ на чертеже ("2 трубы 160 мм методом ГНБ"), в
;; расчёте количества труб не участвует никак (там всё считается от
;; длины прокола). Отдельная константа, а не число прямо в тексте
;; подписи, чтобы диаметр правился в одном месте вместе с остальными
;; параметрами трубы.
(setq *LEP-GNB-PipeDiameter*    160)    ; мм, наружный диаметр трубы

;;--------------------------------------------------------------------
;; ТРЕТЬЯ СТРОКА ПОДПИСИ КЛ - СПОСОБ ПРОКЛАДКИ (2026-07-24)
;;
;; По просьбе пользователя у подписи кабельного пролёта появились
;; дополнительные строки внизу, называющие способ работ:
;;   ГНБ     -> ДВЕ строки: "2 трубы 160 мм" / "методом ГНБ" (число
;;              труб и диаметр подставляются из констант выше, а не
;;              пишутся текстом - иначе подпись разъехалась бы с
;;              ведомостью при первой же правке числа труб);
;;   траншея -> одна строка "в траншее".
;;
;; ⚠️ Только у ПРОЕКТИРУЕМОЙ КЛ. У существующей КЛ способ прокладки не
;; спрашивается вообще (она уже проложена как проложена), METHOD в её
;; XDATA нет - строка просто не добавляется. У ВЛ её нет тем более.
;;--------------------------------------------------------------------

(setq *LEP-Label-Method-Trench* "в траншее")

;; Название позиции в CSV-ведомости. Длина отрезка подставляется в
;; название автоматически, чтобы название не разъехалось с
;; *LEP-GNB-PipeLength*, если её когда-нибудь поменяют.
(setq *LEP-Label-GNB-Pipe*
    (strcat "Труба для ГНБ-прокола (" (rtos *LEP-GNB-PipeLength* 2 0) " м)")
)

;; ✅ ДОБАВЛЕНО 2026-07-22 (по просьбе пользователя): если между ОДНОЙ
;; И ТОЙ ЖЕ парой опор ставится несколько пролётов подряд (несколько
;; проводов на общем участке - например, существующая линия + новая
;; проектируемая до какой-то точки, или несколько разных маршрутов
;; ("фидеров"), которые ЧАСТЬ пути идут по общим опорам, а потом
;; расходятся в разные стороны) - без сдвига все такие линии легли бы
;; ТОЧНО друг на друга (одна и та же геометрия), подписи - друг на
;; друге, нечитаемо. Каждый следующий пролёт на той же паре опор
;; сдвигается перпендикулярно трассе на *LEP-Span-ParallelOffset* м x
;; номер по счёту, ПООЧЕРЁДНО в разные стороны от центра (см.
;; LEP:GetParallelOffset, LEP-SPAN.LSP) - 1-й пролёт остаётся на месте
;; (не смещается вообще), 2-й уходит на +0,3м, 3-й на -0,3м, 4-й на
;; +0,6м и т.д.
;;
;; ⚠️ ИЗМЕНЕНО 2026-08-06: было 0,5 м, стало 0,3 (решение пользователя
;; после обсуждения с коллегой - полметра оказалось слишком много).
;;
;; ⚠️ СКОЛЬКО ПРОВОДОВ ПОМЕЩАЕТСЯ В СИМВОЛ ОПОРЫ. Трапеция опоры -
;; 1,0 м в основании (*LEP-Pole-Sym-Base*), то есть занимает примерно
;; ±0,5 м поперёк трассы. При шаге 0,3 м провода встают на 0, +0,3,
;; -0,3, +0,6 - и ЧЕТВЁРТЫЙ уже вылезает за край опоры. Три помещаются.
;; Оставлено сознательно (решение пользователя): "чертёж делаем не для
;; конкурса, а для проектировщика, он дальше сам решит, как красивее" -
;; вылезший четвёртый провод виден сразу и сам по себе сигнал.
;;
;; ⚠️ ЭТО ЧИСЛО СВЯЗАНО С *LEP-Span-Overlap-Tolerance* ниже: радиус
;; поиска перекрытия должен быть заметно БОЛЬШЕ самого дальнего сдвига,
;; иначе новый пролёт не увидит уже сдвинутые и ляжет на них. Менять
;; одно, не посмотрев на другое, нельзя.
(setq *LEP-Span-ParallelOffset* 0.3)    ; м

;; ✅ ДОБАВЛЕНО 2026-07-22 (по просьбе пользователя): допуск для
;; ГЕОМЕТРИЧЕСКОГО определения, какие маршруты проходят через пару
;; кликнутых опор (LEP:FindRoutesThroughPoints, LEP-SPAN.LSP). Нужен
;; для случая "маршрут 2 проложен ПОВЕРХ уже существующих опор
;; маршрута 1" (общий участок, дальше расходятся) - у самих опор в
;; XDATA записан ТОЛЬКО тот маршрут, которым их создали (маршрут 1),
;; про маршрут 2 они не знают ничего, поэтому определить его можно
;; лишь по ГЕОМЕТРИИ: полилиния маршрута 2 физически проходит рядом
;; с этими опорами.
;;
;; ⚠️ ЗНАЧЕНИЕ ЗАВЫШЕНО СОЗНАТЕЛЬНО (1 м при том, что опоры ставятся
;; проекцией ТОЧНО на трассу): полилинию второго маршрута пользователь
;; рисует РУКАМИ поверх уже стоящих опор - если он не цеплялся
;; привязкой за точки вставки блоков, а вёл "на глаз", попадание может
;; промахнуться на десятки сантиметров. Слишком маленький допуск в
;; этом случае просто НЕ НАЙДЁТ маршрут 2 кандидатом, и программа
;; молча отнесёт пролёт к маршруту 1 (старое поведение) - хуже, чем
;; лишний вопрос. Слишком большой допуск, наоборот, начнёт цеплять
;; чужие трассы, проходящие рядом - тогда вопрос "какой маршрут?"
;; будет появляться там, где выбора на самом деле нет.
(setq *LEP-Route-Detect-Tolerance* 1.0) ; м

;; ✅ ДОБАВЛЕНО 2026-08-05: допуск для ДРУГОГО вопроса - "есть ли у
;; выбранного маршрута ВЕРШИНА там, где стоит кликнутая опора?"
;; (LEP:EnsureVertexAtPoint, LEP-SPAN.LSP).
;;
;; ⚠️ НЕ ПУТАТЬ С *LEP-Route-Detect-Tolerance* ВЫШЕ. Тот отвечает на
;; вопрос "проходит ли ЛИНИЯ маршрута рядом с опорой", этот - "есть ли
;; в этом месте ВЕРШИНА". Разница неочевидная, но именно в зазоре
;; между двумя этими вопросами и жила тихая ошибка, ради которой
;; константа заведена: линия маршрута 2 через опору проходит (значит
;; маршрут-кандидат найден), а вершины у него в этой точке нет -
;; и пролёт молча строился от ближайшей чужой вершины, до которой
;; могли быть десятки метров. Подробный разбор - в шапке
;; LEP:EnsureVertexAtPoint.
;;
;; Значение 1 м, как и у соседа, но по ДРУГОЙ причине: опора стоит
;; РОВНО в вершине своего маршрута (её туда и вставили при постановке),
;; так что в нормальной работе расстояние здесь нулевое, и метр - это
;; чистый запас на случай, если опору двигали вручную и связь
;; GEOMCONSTRAINT почему-то не сработала. Уменьшать смысла нет,
;; увеличивать опасно: чем больше допуск, тем дальше может оказаться
;; вершина, которую программа сочтёт "той самой".
(setq *LEP-Span-VertexGap-Tolerance* 1.0) ; м

;; ✅ ДОБАВЛЕНО 2026-08-20: СХЛОПЫВАНИЕ ВЕРШИН ПЕРЕД ПРОСТАНОВКОЙ
;; РАЗМЕРОВ (LEP:CollapseDimVertices, LEP-SPAN.LSP).
;;
;; ЗАЧЕМ. Размеры ставятся НА КАЖДЫЙ участок между соседними вершинами
;; маршрута (LEP:CreateSpanDimensions) - так задумано ради траншеи
;; "молнией", где надо промерить каждое колено. Пока трасса рисовалась
;; прямой, вершины и опоры совпадали один в один, и вопросов не было.
;;
;; На ЛОМАНОЙ трассе вылезло вот что (случай пользователя 2026-08-20,
;; диагностика по живому чертежу): угловая опора почти всегда ставится
;; рядом с изломом, который пользователь нарисовал руками. Клик мимо
;; излома дальше *LEP-Vertex-Snap-Tolerance* (10 см!) - и
;; LEP:InsertVertexOnRoute честно вставляет ВТОРУЮ вершину рядом с
;; первой. На чертеже из 26 вершин таких пар оказалось пять:
;; 29,25 + 0,75 = 30,00 м, то есть шаг опор целый, а размеров два -
;; "29 м" и "1 м". Второй размер и есть та "хуйня", ради которой всё
;; это писалось.
;;
;; ⚠️ ПОЧЕМУ НЕЛЬЗЯ ПРОСТО "НЕ РИСОВАТЬ КОРОТКИЕ УЧАСТКИ". Тогда
;; сумма подписанных участков перестала бы сходиться с трассой: 0,75 м
;; просто исчезли бы, а размер показывал бы 29 вместо 30. Здесь
;; вершины именно СХЛОПЫВАЮТСЯ: две близкие точки считаются ОДНИМ
;; узлом, и размер идёт от узла до узла - 30 м, как и должно быть.
;;
;; ⚠️ ПОЧЕМУ НЕЛЬЗЯ СХЛОПЫВАТЬ "ВСЁ, ЧТО НА ПРЯМОЙ" (по углу излома).
;; Опоры на прямом участке ВЛ стоят РОВНО коллинеарно, и такой фильтр
;; убил бы все размеры между ними - то самое, ради чего посегментные
;; размеры включали для ВЛ 2026-08-05. Поэтому критерий не угол, а
;; расстояние + наличие блока (см. ниже).
;;
;; NodeGap - на каком расстоянии две вершины считаются одним узлом.
;; 2 м: паразитные пары на живом чертеже давали 0,13-0,80 м, а самый
;; короткий ОСМЫСЛЕННЫЙ участок там же - 3,07 м. Запас с обеих сторон.
(setq *LEP-Dim-NodeGap* 2.0) ; м

;; NodeSnap - на каком расстоянии от вершины блок считается стоящим
;; ИМЕННО В НЕЙ. Из схлопнутой пары представителем становится та
;; вершина, где реально стоит опора (КТП, киоск, маркер) - иначе
;; размер начинался бы в 0,75 м от опоры, и на печати это видно.
;; 0,3 м: опора вставляется РОВНО в вершину (LEP:PlacePoleOnRoute),
;; так что запас нужен только на ручной сдвиг блока.
;; ⚠️ Больше делать нельзя: откосы 2-/3-стоечных опор - это блоки на
;; ТОМ ЖЕ слое, стоящие в *LEP-Pole-Sym-Offset* (2 м) от вершины.
(setq *LEP-Dim-NodeSnap* 0.3) ; м

;; ✅ ДОБАВЛЕНО 2026-08-05: допуски для проверки "а нет ли тут уже
;; размерной линии?" (LEP:DimensionAlreadyThere, LEP-SPAN.LSP).
;;
;; ЗАЧЕМ. Два маршрута могут идти по ОДНИМ И ТЕМ ЖЕ опорам (общий
;; участок двух фидеров). Размеры рисуются при построении пролёта, и
;; второй маршрут рисовал их поверх уже готовых размеров первого.
;; Единственной защитой был счётчик пролётов на ТОЙ ЖЕ ПАРЕ ОПОР
;; (LEP:FindSamePolePairSpans), а у двух маршрутов пары разные - он не
;; срабатывал. Теперь проверяется не "чей это пролёт", а простое
;; "есть ли уже размерная линия на этом месте": чертёж про маршруты
;; ничего не знает, размер - это просто объект на слое LEP-DIM.
;;
;; КАК СЧИТАЕТСЯ. Берём СЕРЕДИНУ нового участка и смотрим, лежит ли
;; она на каком-нибудь существующем размере (расстояние до его отрезка
;; меньше допуска в метрах) И параллельны ли они (угол между ними
;; меньше углового допуска).
;;
;; ⚠️ Проверка по СЕРЕДИНЕ, а не по концам - принципиально. Сравнение
;; концов ловило бы только точные дубли, а на общем участке у второго
;; маршрута вершины стоят не на опорах, а там, где пользователь кликал
;; при рисовании полилинии: его отрезок обычно ДЛИННЕЕ и накрывает
;; несколько старых размеров сразу. Концы при этом не совпадают ни с
;; чем, и проверка по концам пропустила бы ровно половину случаев.
;;
;; ⚠️ Угловой допуск нужен, чтобы не задавить размер, который просто
;; ПЕРЕСЕКАЕТ старый под углом (перекрёсток двух трасс). Без него мы
;; молча теряли бы нужные размеры, а это хуже лишней линии.
;;
;; Метровый допуск = 1 м по той же причине, что и у соседей выше:
;; вторую полилинию рисуют руками поверх стоящих опор, попадание "на
;; глаз" промахивается на десятки сантиметров. Угловой в ГРАДУСАХ
;; (перевод в радианы - в самой функции), 10° - заметно больше любой
;; погрешности ручного рисования и заметно меньше настоящего
;; перекрёстка.
(setq *LEP-Dim-Duplicate-Tolerance* 1.0)  ; м, до линии существующего размера
(setq *LEP-Dim-Duplicate-AngleTol*  10.0) ; градусов, отклонение от параллельности

;; ✅ ДОБАВЛЕНО 2026-08-06: допуски для поиска УЖЕ НАРИСОВАННЫХ ПРОЛЁТОВ
;; рядом с новым (LEP:CountOverlappingSpans, LEP-SPAN.LSP) - по ним
;; считается номер параллельного сдвига.
;;
;; ЗАЧЕМ. Раньше "сколько проводов уже идёт здесь" считалось по
;; СОВПАДЕНИЮ ПАРЫ ХЕНДЛОВ ОПОР (LEP:FindSamePolePairSpans). Это
;; работало для случая, под который и писалось - два провода между
;; ОДНОЙ И ТОЙ ЖЕ парой опор. Но у двух маршрутов, которые совпадают
;; ЧАСТИЧНО (маршрут 2 вливается в маршрут 1 и идёт с ним до общей ТП),
;; пары концов разные - совпадение не находилось, сдвиг не срабатывал,
;; и провода ложились точно друг на друга. Проверка по хендлам умеет
;; отвечать только "та же пара / не та же" и частичное перекрытие не
;; видит в принципе.
;;
;; Считается ТАК ЖЕ, как дубли размерных линий выше: середина отрезка
;; нового пролёта должна лежать на отрезке чужого пролёта И отрезки
;; должны быть параллельны. Считается ОТДЕЛЬНО ДЛЯ КАЖДОГО ОТРЕЗКА -
;; поэтому своя улица маршрута 2 остаётся на месте, а сдвигается только
;; общий с маршрутом 1 участок.
;;
;; ⚠️ РАДИУС ОБЯЗАН БЫТЬ БОЛЬШЕ САМОГО ДАЛЬНЕГО СДВИГА. Уже нарисованные
;; пролёты лежат СО СВОИМ сдвигом (0,3 / -0,3 / 0,6 ...), а новый ищется
;; по несдвинутой трассе. Возьми радиус меньше - и очередной провод
;; просто не увидит дальние и ляжет на них.
;; При шаге 0,3 м и радиусе 1 м самый дальний видимый сдвиг - 0,9 м,
;; то есть ПРИМЕРНО СЕМЬ ПРОВОДОВ в одном коридоре считаются верно,
;; восьмой начнёт ошибаться. Больше семи в одном коридоре пока не
;; встречалось; понадобится - увеличивать радиус ВМЕСТЕ с проверкой,
;; что он не начал цеплять соседние трассы.
(setq *LEP-Span-Overlap-Tolerance* 1.0)  ; м, до линии чужого пролёта
(setq *LEP-Span-Overlap-AngleTol*  10.0) ; градусов, отклонение от параллельности



;=====================================================================
;                      ИМЕНА БЛОКОВ
;=====================================================================
;
; *LEP-Block-Pole* раньше указывал на "test-block" (кружок-заглушка,
; создавался вручную одноразовой командой из LEP-MAKETESTBLOCK.LSP).
; Теперь здесь имя настоящего рабочего символа опоры - трапеция+крест,
; создаётся сама, автоматически, из LEP-POLESYM.LSP при каждой
; загрузке LEP-START. test-block/LEP-MAKETESTBLOCK.LSP больше не
; нужны вообще - файл удалён из проекта 2026-07-10 (см. историю git,
; если понадобится восстановить для отладки).
;
; *LEP-Block-MTP* / *LEP-Block-RLK* (имена блоков МТП/РЛК) УБРАНЫ -
; выяснилось (переписка с пользователем 2026-07-10), что МТП/РЛК/ЩУ/ПУ
; на чертеже НЕ рисуются отдельной графикой, только подписываются
; текстом рядом с нужной опорой (см. *LEP-Label-MTP* и соседние
; константы в разделе "ОКОНЕЧНОЕ ОБОРУДОВАНИЕ" ниже) - отдельные
; блоки для них были бы мёртвым кодом.
;
;=====================================================================

(setq *LEP-Block-Pole*          "LEP-POLE-SYM")



;=====================================================================
;         СИМВОЛ ОПОРЫ (трапеция + крест) - LEP-POLESYM.LSP
;=====================================================================
;
; Схематичный значок опоры на плане - трапеция (по сути квадрат 1x1м,
; у которого узкая сторона сужена до 0,7м) + крест через центр (обе
; линии полностью на *LEP-Pole-Sym-Cross* м, торчат за края трапеции -
; подтверждено пользователем по референс-скриншотам блоков компании).
; Точка вставки блока - геометрический центр (там же, где сходится
; крест).
;
; РАЗВОРОТ (по просьбе пользователя, 2026-07-10): широкая сторона
; трапеции всегда смотрит к НАЧАЛУ маршрута, узкая - к КОНЦУ. Угол
; поворота при вставке считается по направлению локального отрезка
; трассы в точке установки - см. LEP:GetPoleRotation в LEP-POLESYM.LSP.
;
;=====================================================================

(setq *LEP-Pole-Sym-Base*       1.0)    ; м, ширина широкой стороны (к началу маршрута)
(setq *LEP-Pole-Sym-Top*        0.7)    ; м, ширина узкой стороны (к концу маршрута)
(setq *LEP-Pole-Sym-Height*     1.0)    ; м, высота трапеции
(setq *LEP-Pole-Sym-Cross*      1.07)   ; м, длина каждой из двух линий креста целиком (не от центра)
(setq *LEP-Pole-Sym-Offset*     2.0)    ; м, расстояние между трапециями (главная опора -> откос, и между опорами в блоке МТП) - одно число на все случаи (было 1.0, поправлено по просьбе пользователя 2026-07-10)

;; Толщина линии символа опоры - зависит от СТАТУСА объекта (Проект.
;; жирнее Сущ., по просьбе пользователя), а не запечена в саму
;; геометрию блока (иначе пришлось бы держать два разных блока на
;; каждый статус). Технически это свойство LWEIGHT (группа DXF 370) у
;; самого вставленного INSERT - геометрия ВНУТРИ блока имеет
;; LWEIGHT = ByBlock (-2, см. LEP-POLESYM.LSP), поэтому значение,
;; выставленное на INSERT при вставке, "протекает" на всю вложенную
;; графику (трапецию и крест) сразу. Значения - стандартные коды
;; AutoCAD LWEIGHT в сотых долях мм (0.50мм / 0.13мм).
(setq *LEP-LWeight-Proj*        50)
(setq *LEP-LWeight-Exist*       13)

;; Крест внутри символа - ВСЕГДА серый, независимо от цвета/статуса
;; самой опоры (по просьбе пользователя 2026-07-10) - в отличие от
;; толщины линии (которая через LWEIGHT=ByBlock наследуется от
;; INSERT), цвет креста задаётся ПРЯМО в геометрии блока (группа DXF
;; 62), поэтому не меняется вместе со статусом/цветом слоя опоры.
(setq *LEP-Color-PoleCross*     8)      ; Серый

;; Допуск "это одна и та же точка маршрута" - используется в
;; LEP:InsertVertexOnRoute (LEP-POLE.LSP), чтобы НЕ вставлять вторую,
;; почти совпадающую вершину полилинии, если клик пришёлся рядом с
;; УЖЕ существующей вершиной (реальный излом трассы - именно так
;; обычно кликают угловые опоры). Без этой проверки GEOMCONSTRAINT
;; ловил конфликт "over-constrain" на дублирующихся вершинах в одной
;; точке (см. историю чата, баг найден 2026-07-10 на угловой опоре).
(setq *LEP-Vertex-Snap-Tolerance* 0.1)  ; м



;=====================================================================
;   СПРАВОЧНИК СТОЕК: ТИП ОПОРЫ -> МАРКА СТОЙКИ + ИХ КОЛИЧЕСТВО
;=====================================================================
;
; ✅ ПЕРЕПИСАНО 2026-08-03. Раньше здесь был *LEP-PoleColumns* - просто
; "сколько трапеций рисовать". Теперь та же таблица хранит ЕЩЁ И МАРКУ
; ЖЕЛЕЗОБЕТОННОЙ СТОЙКИ, из которой опора собрана.
;
; ЗАЧЕМ. Требование коллеги пользователя (2026-08-03): "тип опоры
; и стойка - разные вещи. П23 это ТИП опоры, он состоит из одной стойки
; СВ-95. А23 - тип опоры из ДВУХ стоек СВ-95. В спецификации нужно
; именно количество стоек". То есть закупают не "опору А23", а две
; штуки железобетонных изделий СВ-95-3, и в ведомости должны стоять
; они.
;
; Ключевая мысль, которая связывает чертёж со спецификацией: ОТКОС НА
; ЧЕРТЕЖЕ - ЭТО И ЕСТЬ ВТОРАЯ (ТРЕТЬЯ) СТОЙКА, просто вкопанная под
; углом. Поэтому "сколько трапеций рисуем" и "сколько стоек покупаем" -
; ОДНО И ТО ЖЕ ЧИСЛО, и хранить его в двух разных списках было бы
; прямой дорогой к расхождению чертежа с ведомостью. Один список -
; один источник правды:
;   рисование  - LEP:GetPoleColumns (LEP-POLESYM.LSP);
;   ведомость  - ЭТАП 2 в LEP-REPORT.LSP.
;
; ФОРМАТ СТРОКИ: ("тип опоры" "марка стойки" количество)
;   (cadr ...) - марка, (caddr ...) - количество.
;
; ЧТО ОЗНАЧАЕТ КОЛИЧЕСТВО:
;   1 - одиночная опора (промежуточная, поддержки не требует);
;   2 - главная стойка + 1 откос (анкерная, либо угловая промежуточная);
;   3 - главная стойка + 2 откоса (угловая анкерная - тянет сразу в
;       двух направлениях излома маршрута, поддержка нужна в обе
;       стороны).
;
; ОТКУДА ВЗЯТЫ ДАННЫЕ (2026-08-03, поиск по каталогам + ответы коллеги):
;   * семейство "20-3Н" (ВЛЗ 6-20 кВ, СИП-3, альбом 27.0002) - числа
;     сверены с published спецификациями опор, совпали с теми, что уже
;     стояли в программе;
;   * семейство "23" (ВЛИ 0,4 кВ) - ⚠️ шифр живёт в ДВУХ альбомах с
;     РАЗНОЙ конструкцией: серия 3.407.1-143 (с подкосами, А23 = 2
;     стойки) и проект 25.0017 (одностоечные, с опорно-анкерной
;     плитой, А23 = 1 стойка). Коллега прямо подтвердил "А-23 - 2
;     стойки" -> взят вариант с подкосами. ⚠️ Он назвал ТОЛЬКО А23,
;     числа для УП23 (2) и УА23 (3) взяты по той же серии;
;   * семейство "21" (проект 21.0112) - альбом называется "опоры
;     ОДНОСТОЕЧНОЙ конструкции", отсюда 1. Альбом допускает СВ105-5
;     ИЛИ СВ110-5; коллега на прямой вопрос ответил "СВ-110-5";
;   * написание марки - "СВ-95-3" / "СВ-110-5", как коллега сказал пишут
;     в их проектах (каталоги пишут слитно, "СВ95-3" - нам важно то,
;     что уходит в документы заказчика).
;
; ⚠️ УП21 И К21 РАНЬШЕ ОТСУТСТВОВАЛИ В ЭТОМ СПИСКЕ. При этом в старом
; комментарии УП21 был подробно ОПИСАН ("исключение из логики У+П = 2
; столба, 1 столб, подтверждено пользователем") - то есть комментарий
; описывал то, чего в данных не было. Держалось на тихом фолбэке
; LEP:GetPoleColumns ("не нашёл тип - считай 1"), который случайно
; давал верный ответ. Для стоек такой фолбэк уже не спасёт (марку
; выдумать неоткуда), поэтому оба типа внесены ЯВНО.
;
; ⚠️ ДОБАВЛЯЯ НОВЫЙ ТИП ОПОРЫ: он должен попасть И сюда, И в
; *LEP-PoleTypes* ниже. Здесь - иначе опора не попадёт в ведомость
; (появится громкая строка "НЕТ В СПРАВОЧНИКЕ СТОЕК", см. ЭТАП 2
; в LEP-REPORT.LSP - специально громкая, чтобы не потерять материал
; молча). Там - иначе тип нельзя будет выбрать при расстановке.
;
;=====================================================================

(setq *LEP-PoleStands*
    '(
        ;; тип опоры    марка стойки   кол-во стоек
        ("П23"          "СВ-95-3"      1)
        ("УП23"         "СВ-95-3"      2)
        ("А23"          "СВ-95-3"      2)
        ("УА23"         "СВ-95-3"      3)

        ("УП21"         "СВ-110-5"     1)
        ("К21"          "СВ-110-5"     1)

        ("П20-3Н"       "СВ-110-5"     1)
        ("УП20-3Н"      "СВ-110-5"     2)
        ("А20-3Н"       "СВ-110-5"     2)
        ("УА20-3Н"      "СВ-110-5"     3)
    )
)

;; Префикс строки ведомости для стойки. Отдельной константой, а не
;; текстом в коде: если завтра в спецификации потребуется писать
;; "Стойка ж/б" или вообще без слова - правка в одном месте.
(setq *LEP-Label-Stand-Prefix* "Стойка ")



;=====================================================================
;                НАСТРОЙКИ КАЛИБРОВКИ
;=====================================================================

(setq *LEP-ReferenceLengths*
      '(10.0 20.0 50.0 100.0))

;=====================================================================
;                 СПИСОК ТИПОВ ОПОР
;
; Используется:
; - выбор пользователем;
; - подписи;
; - ведомость.
;
; Первый элемент:
; отображаемое название.
;
; Второй элемент:
; условный код для учета.
;
;=====================================================================


(setq *LEP-PoleTypes*

    '(

        ("П23"       . "П23")

        ("УП23"      . "УП23")

        ("А23"       . "А23")

        ("УА23"      . "УА23")

        ("УП21"      . "УП21")

        ("К21"       . "К21")

        ("П20-3Н"    . "П20-3Н")

        ("А20-3Н"    . "А20-3Н")

        ("УА20-3Н"   . "УА20-3Н")

        ("УП20-3Н"   . "УП20-3Н")

    )

)
;=====================================================================
;                 СПИСОК ТИПОВ МАТЕРИАЛОВ
;
;
;=====================================================================


(setq *LEP-UseDCL* nil) ; T = диалог со списком (мышкой), nil = ввод номером в консоли - быстрее, по опыту использования


;=====================================================================
;             КЛАСС НАПРЯЖЕНИЯ МАРШРУТА (LEP-ROUTE)
;=====================================================================
;
; Выбирается ОДИН РАЗ при построении маршрута (LEP-ROUTE), а не на
; каждом пролёте - в жизни напряжение не меняется посреди трассы:
; между 10кВ и 0,4кВ участками всегда стоит трансформатор (МТП), а
; значит с точки зрения этой программы это уже НОВЫЙ маршрут (см.
; переписку с пользователем, 2026-07-10). Класс маршрута хранится в
; его XDATA (ключ VCLASS, LEP-DATA.LSP) и дальше используется:
;   - LEP-SPAN выбирает список марок провода по классу маршрута
;     (*LEP-WireTypes-VL-10* для 10кВ, *LEP-WireTypes-VL-04* для
;     0,4кВ - СИП-3 бывает ТОЛЬКО для высокого напряжения (магистраль),
;     СИП-2 ТОЛЬКО для низкого 0,6-1кВ - это разные провода физически,
;     предлагать не тот список для не того класса нельзя);
;   - LEP-POLE берёт отсюда вторую строку подписи опоры
;     ("ВЛЗ-10 кВ" / "ВЛИ-0,4 кВ", *LEP-VoltageClassLabel* ниже).
;
;=====================================================================

;; ✅ ДОБАВЛЕНО 2026-07-22 (по просьбе пользователя): третий класс
;; напряжения - "6 кВ". Цвет слоя/опор у 6кВ ПОКА СОЗНАТЕЛЬНО НЕ свой -
;; переиспользует те же 2 слоя, что и 10кВ (LEP-SPAN.LSP/LEP-POLE.LSP -
;; их ветка "если статус/класс не 0,4кВ" уже трактует "6" точно так же,
;; как "10", отдельного слоя заводить не пришлось). Пользователь прямо
;; сказал "дальше видно будет" - если позже понадобится отличать 6кВ
;; от 10кВ цветом, придётся завести *LEP-Layer-Proj-VL-6*/*-Pole-6* по
;; тому же образцу, что и *-04* (см. раздел "СЛОИ" выше).
(setq *LEP-VoltageClasses*
    '(
        ("10 кВ"  . "10")
        ("6 кВ"   . "6")
        ("0,4 кВ" . "04")
    )
)

(setq *LEP-VoltageClassLabel*
    '(
        ("10" . "ВЛЗ-10 кВ")
        ("6"  . "ВЛЗ-6 кВ")
        ("04" . "ВЛИ-0,4 кВ")
    )
)

(setq *LEP-WireTypes-VL-10*
    (list
        (cons "СИП-3 3х(1х70 мм2)" "70")
        (cons "СИП-3 3х(1х95 мм2)" "95")
    )
)

;; ⚠️ ОТКРЫТЫЙ ВОПРОС (как и у *LEP-WireTypes-VL-10* выше - см.
;; "Известные открытые проблемы" в LEP-README.md): марки временно
;; СКОПИРОВАНЫ с 10кВ-списка "на правдоподобный вид" - СИП-3
;; действительно применяется и на 6кВ ЛЭП, но КОНКРЕТНЫЕ сечения/марки
;; для 6кВ пользователь не прислал. Поправить эту строку, как только
;; будут точные марки - остальной код (LEP-SPAN.LSP) их не хардкодит,
;; список подтягивается отсюда автоматически.
(setq *LEP-WireTypes-VL-6*
    (list
        (cons "СИП-3 3х(1х70 мм2)" "70")
        (cons "СИП-3 3х(1х95 мм2)" "95")
    )
)

(setq *LEP-WireTypes-VL-04*
    (list
        (cons "СИП-2 3х95+1х95 мм2" "95")
        (cons "СИП-2 3х70+1х70 мм2" "70")
    )
)

;; ✅ 2026-07-24: заглушка "Кабель (марка неизв.) 120 мм2" заменена на
;; РЕАЛЬНУЮ марку - пользователь прислал её по факту первого живого
;; проекта с кабелем. Расшифровка марки (чтобы не гадать при следующей
;; правке): А - алюминиевая жила, Пв - изоляция из сшитого полиэтилена,
;; Б - броня из стальных лент, б - без подушки под бронёй, Шп -
;; наружный шланг (оболочка) из полиэтилена.
;;
;; ⚠️ Список из ОДНОЙ строки - это нормально и ничего не ломает
;; (LEP:ChooseFromList в LEP-SPAN.LSP просто покажет один пункт).
;; Появятся другие сечения/марки - дописывать сюда, код их нигде не
;; хардкодит. Второй элемент пары ("120") - СЕЧЕНИЕ, оно уходит в
;; XDATA пролёта отдельным ключом SECTION, поэтому при добавлении
;; новой строки его надо указывать честно, а не копировать.
(setq *LEP-WireTypes-KL*
    (list
        (cons "АПвБбШп 120 мм2" "120")
        (cons "АПвБбШп 4x150 мм2" "150")
    )
)



;=====================================================================
;                 ОКОНЕЧНОЕ ОБОРУДОВАНИЕ МАРШРУТА (LEP-END)
;=====================================================================
;
; Конец трассы ЛЭП оформляется по-разному в зависимости от класса
; напряжения (см. присланные пользователем скриншоты реальных
; чертежей, 2026-07-10):
;   10 кВ (крупный заявитель)  -> 3 опоры типа *LEP-End-PoleType*
;       подряд (шаг *LEP-End-MTP-Spacing1*/-Spacing2*), 1-я с подписью
;       РЛК, 2-я - МТП, 3-я - ЩУ;
;   0,4 кВ (мелкий заявитель)  -> прибор учёта на опоре. ⚠️ 2026-08-11:
;       опору под него LEP-END БОЛЬШЕ НЕ СТАВИТ - её ставят обычной
;       командой LEP-POLE (тип "П23"), а LEP-END только навешивает на
;       неё прибор: строка в подпись + вид в XDATA. До 2026-08-11 опора
;       ставилась автоматически, типом *LEP-End-PoleType-PU*.
; РЛК/МТП/ЩУ/ПУ - НЕ отдельная графика на чертеже, только текстовые
; подписи рядом с соответствующей опорой (подтверждено пользователем).
;
;=====================================================================

(setq *LEP-End-PoleType*        "П20-3Н")

;; ⚠️ ДОБАВЛЕНО 2026-08-03 (прямое указание пользователя): у окончания
;; "ПУ" опора теперь ДРУГОГО типа - П23, а не общий *LEP-End-PoleType*.
;;
;; Почему ОТДЕЛЬНАЯ константа, а не просто правка *LEP-End-PoleType*
;; выше: та одна константа обслуживает СРАЗУ ВСЁ оконечное
;; оборудование - и ПУ, и СТП, и все три опоры МТП (РЛК/МТП/ЩУ).
;; Пользователь просил поменять тип именно у ПУ, поэтому менять общую
;; константу нельзя - молча переехали бы и МТП со СТП, а на чертеже
;; это выглядело бы как "программа сама себе что-то напридумывала".
;;
;; Если окажется, что П23 нужен и остальным окончаниям - достаточно
;; поставить "П23" в *LEP-End-PoleType* выше, эта строка тогда просто
;; продублирует его, ничего не сломав.
;;
;; ⚠️ Тип ОБЯЗАН присутствовать в двух списках выше, иначе:
;;   *LEP-PoleStands* - и марка стойки для ведомости, и число трапеций
;;       для чертежа. Нет типа -> в CSV громкая строка "НЕТ В
;;       СПРАВОЧНИКЕ СТОЕК" вместо материала (ЭТАП 2, LEP-REPORT.LSP);
;;   *LEP-PoleTypes*  - без него тип нельзя выбрать при обычной
;;       расстановке опор (LEP-POLE.LSP).
;; Проверено на 2026-08-03: "П23" есть в обоих. В *LEP-PoleStands* - со
;; значением ("СВ-95-3" 1): одна стойка, то есть одна трапеция, как и у
;; "П20-3Н", геометрия символа не меняется; в ведомость от опоры ПУ
;; пойдёт строка "Стойка СВ-95-3".
;;
;; ⚠️ 2026-08-11: КОНСТАНТА БОЛЬШЕ НЕ ИСПОЛЬЗУЕТСЯ КОДОМ. Пункт меню
;; "ПУ" в LEP-END больше НЕ создаёт опору сам (решение пользователя -
;; два пункта, "ПУ" и "ПУ на существующую опору", слиты в один "ПУ на
;; опору", который только навешивает прибор на УЖЕ СТОЯЩУЮ опору).
;; Тип опоры под ПУ теперь выбирает пользователь руками в LEP-POLE -
;; "П23" есть в *LEP-PoleTypes* выше, выбирается как любой другой.
;;
;; Константа СОЗНАТЕЛЬНО оставлена, а не удалена: если решим вернуть
;; автоматическую постановку опоры под ПУ, она понадобится ровно в том
;; же виде. Удалять её "как мусор" не надо.
(setq *LEP-End-PoleType-PU*     "П23")

(setq *LEP-End-MTP-Spacing1*    3.0)    ; м, опора1 (РЛК) -> опора2 (МТП)
(setq *LEP-End-MTP-Spacing2*    2.0)    ; м, опора2 (МТП) -> опора3 (ЩУ)

(setq *LEP-Label-RLK*           "РЛК")

;; *LEP-Label-MTP* - ⚠️ ФИКС 2026-07-16: оставлена как ЗНАЧЕНИЕ ПО
;; УМОЛЧАНИЮ/для ОБРАТНОЙ СОВМЕСТИМОСТИ со старыми МТП, поставленными
;; ДО того, как появился выбор мощности (у них в XDATA записан просто
;; общий код "MTP", без указания мощности - см. LEP:GetEquipLabel,
;; LEP-REPORT.LSP). Формат переведён на "мощность/ВН/НН" (160 кВА,
;; 10 кВ высокая сторона, 0,4 кВ низкая) - тот же стандарт, что и у
;; новой строки "МТП-250/10/0,4" ниже, было "МТП-160 кВА" (только
;; мощность, без классов напряжения).
(setq *LEP-Label-MTP*           "МТП-160/10/0,4")

;; Список выбора мощности МТП (2026-07-16, по просьбе пользователя -
;; "МТП-250/10/0,4" тоже встречается у заявителей, не только 160).
;; Для НОВЫХ МТП выбранная строка целиком уходит в XDATA как EQUIP
;; (LEP-END.LSP) - в отличие от старого поведения (*LEP-Label-MTP*
;; выше), название конкретного МТП теперь не "вычисляется заново" из
;; конфига при каждой генерации ведомости, а хранится в самой опоре -
;; иначе разные по мощности МТП было бы не отличить друг от друга в
;; ведомости (обе показывали бы одно и то же название из конфига).
;;
;; ✅ ДОБАВЛЕНО 2026-07-24 (по просьбе пользователя): МТП на 6 кВ - те
;; же мощности (160/250), отличается только средняя часть строки
;; "мощность/ВН/НН": высокая сторона 6 кВ вместо 10 кВ. Больше НИЧЕГО
;; для 6 кВ менять не пришлось - геометрия блока МТП (3 опоры, шаг
;; 3 м/2 м), подписи РЛК/ЩУ, углы разведения подписей и слой опор от
;; класса напряжения не зависят.
;;
;; ⚠️ Список СОЗНАТЕЛЬНО НЕ фильтруется по классу маршрута (решение
;; пользователя 2026-07-24): программа знает VCLASS маршрута и МОГЛА БЫ
;; показывать только подходящие два пункта, но пользователь выбрал
;; видеть все четыре - на случай, если понадобится поставить МТП не того
;; класса, что у маршрута. То есть ответственность за выбор строки -
;; на пользователе, программа тут не подстраховывает.
(setq *LEP-MTP-Types*
    '(
        ("МТП-160/10/0,4" . "МТП-160/10/0,4")
        ("МТП-250/10/0,4" . "МТП-250/10/0,4")
        ("МТП-160/6/0,4"  . "МТП-160/6/0,4")
        ("МТП-250/6/0,4"  . "МТП-250/6/0,4")
    )
)

(setq *LEP-Label-SchU*          "ЩУ")
(setq *LEP-Label-PU*            "ПУ")

;=====================================================================
;              ВИДЫ ПРИБОРОВ УЧЁТА (ПУ) - 2026-08-11
;=====================================================================
;
; До 2026-08-11 "ПУ" был ОДНОЙ плоской строкой: и на чертеже, и в
; ведомости все приборы учёта сливались в одну позицию. Со слов
; коллеги-электрика (2026-08-04) это неверно - за словом "ПУ" стоят
; РАЗНЫЕ изделия, и закупаются они по отдельности.
;
; ⚠️ ДВА НЕЗАВИСИМЫХ ПРИЗНАКА, которые в живой речи называют одной
; фразой и потому очень легко склеить:
;   схема включения - ПРЯМОЕ (весь ток течёт через счётчик; предел
;       ~100 А по ПУЭ, дальше счётчиков прямого включения просто не
;       выпускают) или ПОЛУКОСВЕННОЕ (напряжение подаётся напрямую, а
;       ток - через трансформаторы тока, понижающие его до 5 А);
;   исполнение и место - СПЛИТ на опоре (измерительный модуль висит на
;       проводах ответвления, дисплей у потребителя) / в ЩИТЕ (ЩУ) / в
;       кабельном киоске.
;
; ⚠️ ПОРОГ - ПО ТОКУ (100 А), А НЕ ПО МОЩНОСТИ. Практические ориентиры
; коллеги ("сплит - случай на 15 кВт", "полукос - как правило больше
; 50 кВт") - это ПРИВЫЧКА, а не расчёт: 100 А это ~66 кВт на трёхфазном
; вводе 0,38 кВ и ~22 кВт на однофазном 0,22 кВ, то есть ни один из
; ориентиров в порог не упирается. Поэтому программа ОБЯЗАНА
; СПРАШИВАТЬ вид ПУ и НЕ ИМЕЕТ ПРАВА вычислять его из мощности
; заявителя - решение принимает проектировщик.
;
; ⚠️⚠️ ФОРМУЛИРОВКИ НИЖЕ - ЧЕРНОВЫЕ, С КОЛЛЕГОЙ НЕ СОГЛАСОВАНЫ.
; Дословно подтверждена только одна - "ПУ полукос". Остальные написаны
; "по смыслу", чтобы механика заработала целиком и её можно было
; посмотреть на живом чертеже. Эти строки уходят в CSV ЗАКАЗЧИКУ
; дословно, поэтому пока действует флаг *LEP-PU-Draft* ниже: при каждом
; выборе вида ПУ в консоль печатается предупреждение. Согласуем
; формулировки - правим ЭТОТ список и ставим флаг в nil, код не
; трогаем.
;
; Устройство - по образцу *LEP-MTP-Types* выше: пара (пункт меню .
; строка спецификации), и в XDATA (ключ EQUIP) уходит ПРАВАЯ ЧАСТЬ
; ЦЕЛИКОМ. Вычислять название заново при генерации ведомости нельзя -
; все виды снова схлопнутся в одну строку, это уже ловили на МТП
; 2026-07-16.
;
; Пункт "вид не уточнён" - НЕ заглушка "на потом", а рабочий случай:
; иногда на стадии черчения ещё не известно, какой прибор согласует
; сетевая. Он даёт ровно прежнее поведение (строка "ПУ"), то есть
; отказ от уточнения ничего не ломает.
;=====================================================================

;; Виды ПУ, которые вешаются НА ОПОРУ (LEP-END, пункт "ПУ на опору").
(setq *LEP-PU-Types*
    '(
        ("ПУ сплит - прямое включение, на опоре" . "ПУ сплит прямого включения")
        ("ПУ полукос - полукосвенное, в щит"     . "ПУ полукос")
        ("ПУ - вид не уточнён"                   . "ПУ")
    )
)

;; Виды ПУ, которые стоят В КАБЕЛЬНОМ КИОСКЕ (LEP-END, пункт "КК").
;;
;; ⚠️ Список ОТДЕЛЬНЫЙ, а не тот же самый: сплит на опоре в киоске не
;; бывает по определению (сплит - это модуль на проводах ответвления),
;; а прямое включение в киоске - это, со слов коллеги, ДРУГОЙ прибор,
;; чем сплит, и как он называется в спецификации - пока не выяснено.
;; Полукосвенный же в киоске и в щите - ОДНА И ТА ЖЕ строка, поэтому
;; она здесь дословно повторяет строку из списка выше: так эти приборы
;; сложатся в ведомости в одну позицию, что для закупки и правильно.
(setq *LEP-PU-Types-KK*
    '(
        ("ПУ полукос - полукосвенное"      . "ПУ полукос")
        ("ПУ прямого включения (в киоске)" . "ПУ прямого включения")
        ("ПУ - вид не уточнён"             . "ПУ")
    )
)

;; Короткая метка ДЛЯ ПОДПИСИ НА ЧЕРТЕЖЕ.
;;
;; ⚠️ Строка для ведомости и строка для выноски - РАЗНЫЕ, и это
;; осознанно (тот же принцип, что LEP:GetRealLength / LEP:GetDisplayLength
;; у пролётов). Подписи опор и так двух-трёхстрочные; "ПУ сплит прямого
;; включения" второй строкой полезет на соседние объекты, а закупщику в
;; CSV нужна как раз полная формулировка.
;;
;; Ключ - строка спецификации (правая часть списков выше), значение -
;; что писать на чертеже. Вида нет в этой таблице -> на чертеже
;; печатается сама строка спецификации целиком (см. LEP:GetPuShortLabel
;; в LEP-END.LSP): длинно, но никогда не молча-неверно.
(setq *LEP-PU-ShortLabels*
    '(
        ("ПУ сплит прямого включения" . "ПУ сплит")
        ("ПУ полукос"                 . "ПУ полукос")
        ("ПУ прямого включения"       . "ПУ прям.")
        ("ПУ"                         . "ПУ")
    )
)

;; T - формулировки видов ПУ ещё не согласованы с коллегой, при каждом
;; выборе печатать предупреждение в консоль. Согласуем - поставить nil
;; (предупреждение исчезнет, больше ничего не изменится).
(setq *LEP-PU-Draft*            T)

;; ✅ ДОБАВЛЕНО 2026-07-22 (по просьбе пользователя): СТП - трансформатор
;; на ОДНОЙ опоре (не путать с МТП - 3 опоры). Пока БЕЗ отдельной
;; графики (маленький квадратик сбоку - отложено, "давай пока текстом"):
;; ставится одна опора (тот же механизм, что у ПУ), подпись как у
;; обычной опоры первой строкой + вторая строка "+ СТП-XX кВА"
;; (LEP:CreatePoleLabel, ClassLabel-параметр). В отличие от
;; *LEP-MTP-Types* - БЕЗ классов напряжения в строке (пользователь
;; явно попросил именно такой, более простой формат для СТП).
(setq *LEP-STP-Types*
    '(
        ("СТП-25 кВА" . "СТП-25 кВА")
        ("СТП-40 кВА" . "СТП-40 кВА")
        ("СТП-63 кВА" . "СТП-63 кВА")
    )
)

;; ✅ ДОБАВЛЕНО 2026-07-22 (по просьбе пользователя): КТП - наземная
;; трансформаторная подстанция (НЕ на опоре, в отличие от МТП/СТП).
;; Номер/мощность/марка - СВОБОДНЫЙ ввод (пользователь: "нет живых
;; примеров из жизни чтоб допилить" список), поэтому фиксированного
;; списка здесь, в отличие от *LEP-MTP-Types*/*LEP-STP-Types*, нет -
;; см. LEP:GetString-запросы в LEP-END.LSP.
;;
;; Графика (прямоугольник + треугольник-значок трансформатора) - на
;; уже существующих, ранее НЕ использовавшихся слоях подстанций
;; (*LEP-Layer-Proj-TP*/*LEP-Layer-Exist-TP*, были заведены давно, но
;; простаивали - МТП/РЛК/ЩУ/ПУ оказались текстом без графики, а КТП
;; наконец даёт им применение).
;;
;; Размер прямоугольника - 3х5 м, ПРИКИДКА пользователя ("дальше
;; допилим", т.е. не финальное значение). Треугольник - ЗАЛИВКА ОДНИМ
;; ЦВЕТОМ (SOLID), БЕЗ градиента (пользователь явно попросил градиент
;; пока не делать) - цвет треугольника ФИКСИРОВАННЫЙ (не зависит от
;; статуса Проект/Сущ), тот же принцип, что и у серого креста в
;; символе опоры (*LEP-Color-PoleCross*).
(setq *LEP-KTP-Width*          3.0)  ; м
(setq *LEP-KTP-Height*         5.0)  ; м
(setq *LEP-Color-KTP-Symbol*   1)    ; Красный (ACI) - треугольник-значок трансформатора

;; ✅ ДОБАВЛЕНО 2026-07-24: ВЫСОКАЯ СТОРОНА КТП спрашивается отдельно.
;;
;; ⚠️ Это ФИКС, а не новая хотелка. Вторая строка подписи КТП имеет
;; формат "мощность/ВН/НН", и класс высокой стороны раньше брался ИЗ
;; КЛАССА МАРШРУТА, на котором стоит КТП. Пока КТП ставили на 10-кВ
;; трассу, это случайно совпадало. Но КТП - это ГРАНИЦА двух классов:
;; на входе 10 или 6 кВ, на выходе 0,4 кВ, и трасса от КТП к заявителю
;; вполне может быть 0,4 кВ (реальный случай пользователя 2026-07-24:
;; КТП -> два кабеля 0,4 кВ -> кабельный киоск). На такой трассе старая
;; логика давала в подписи мусор "160/04/0,4 кВ" - и код класса вместо
;; человекочитаемого "0,4", и логически неверно: высокая сторона к
;; классу ЭТОЙ трассы отношения не имеет.
(setq *LEP-KTP-HighSide*
    '(
        ("10 кВ" . "10")
        ("6 кВ"  . "6")
    )
)


;=====================================================================
;    КК - КАБЕЛЬНЫЙ КИОСК (LEP-KKSYM.LSP / LEP-END.LSP) - 2026-07-24
;=====================================================================
;
; ✅ ДОБАВЛЕНО 2026-07-24 по реальному случаю пользователя: из КТП
; выходят два кабеля 0,4 кВ и идут к заявителю, где НЕТ ни опор, ни
; МТП - стоит просто кабельный киоск, а в нём приборы учёта (в том
; случае - два). До этого дня в проекте не было ни киоска, ни вообще
; возможности закончить кабель чем-то, кроме опоры.
;
; Устроен по образцу КТП (LEP-KTPSYM.LSP): блок-символ, создаваемый
; ОДИН раз через entmake, ставится кликом рядом с трассой (проекция +
; новая вершина + GEOMCONSTRAINT - ровно как опора и КТП), своя XDATA
; (TYPE = "KK"), своя строка в ведомости.
;
; Графика - ПРОСТОЙ ПРЯМОУГОЛЬНИК, БЕЗ значка внутри (решение
; пользователя 2026-07-24: у КТП внутри треугольник-трансформатор,
; потому что там трансформатор и есть; в киоске трансформатора нет,
; рисовать внутри нечего).
;
; ⚠️ Размер 1х2 м - ПРИКИДКА, ровно как было с КТП ("дальше допилим").
; Не финальное значение, менять здесь.
;
; Слой - те же *LEP-Layer-Proj-TP*/*LEP-Layer-Exist-TP*, что и у КТП:
; отдельный слой заводить не стали, т.к. ведомость и так различает
; КТП и КК по ключу TYPE в XDATA, а не по слою (см. ЭТАП 2.6 в
; LEP-REPORT.LSP - проверка TYPE там была с самого начала).
;
; Приборы учёта (ПУ) в киоске - СЧЁТЧИК, а не отдельные объекты:
; спрашивается их количество, оно пишется в XDATA киоска (ключ
; PUCOUNT) и попадает в ведомость отдельной строкой "ПУ" в штуках.
; Заводить на каждый ПУ отдельный объект смысла нет - внутри киоска
; они ничем на плане не отличаются друг от друга.
;
;=====================================================================

(setq *LEP-KK-Width*           1.0)  ; м, ПРИКИДКА - уточнить по факту
(setq *LEP-KK-Height*          2.0)  ; м, ПРИКИДКА - уточнить по факту
(setq *LEP-Label-KK*           "КК") ; первая строка подписи киоска
(setq *LEP-Report-Label-KK*    "Кабельный киоск")  ; название строки в ведомости


;=====================================================================
;   ТОЧКА СМЕНЫ СПОСОБА ПРОКЛАДКИ (LEP-TRANSSYM.LSP) - 2026-07-24
;=====================================================================
;
; ✅ ДОБАВЛЕНО 2026-07-24 по реальному случаю: трасса идёт от КТП под
; углом 90°, первый участок надо пройти ГНБ (проколом), второй -
; обычной траншеей. Способ прокладки (*LEP-Layer-Proj-KL-GNB*/
; *-Trench*) спрашивается ОДИН РАЗ НА ПРОЛЁТ, а пролёт задаётся ДВУМЯ
; ОБЪЕКТАМИ - значит, чтобы поделить кабельный участок надвое, в точке
; перехода должен стоять какой-то объект. Опоры там нет и быть не
; должно (её посчитала бы ведомость), КТП/киоск - тем более.
;
; Отсюда - маркер: пустышка без всякого смысла для сметы, нужная
; ТОЛЬКО для того, чтобы за неё можно было "зацепить" конец пролёта.
; Ставится на трассу тем же механизмом, что КТП и киоск (проекция
; клика + вершина + GEOMCONSTRAINT), и дальше чертятся два обычных
; пролёта: КТП -> маркер (ГНБ), маркер -> киоск (траншея).
;
; ⚠️ СЛОЙ НЕПЕЧАТАЕМЫЙ (прямое требование пользователя: "кружок не
; выводится на печать или PDF") - тот же приём, что у служебной линии
; маршрута и у GPS-кружков: LEP:SetLayerNoPlot в LEP-SETUP.LSP. Это
; рабочая пометка для черчения, а не элемент готового чертежа. На
; готовом плане переход и так виден: участки ГНБ и траншеи лежат на
; РАЗНЫХ слоях с разными цветами.
;
; ⚠️ Подписи у маркера НЕТ СОЗНАТЕЛЬНО. Подпись рисуется на печатаемом
; текстовом слое и полезла бы в PDF - ровно то, чего просили избежать,
; и при этом она ничего не добавляет: где кончается прокол, видно по
; смене цвета линии.
;
; ⚠️ В ВЕДОМОСТИ НЕ УЧИТЫВАЕТСЯ (решение пользователя) - это не
; материал, а граница двух видов работ, кабель в этой точке не
; разрезается, покупать нечего. Отдельных действий для этого не
; потребовалось: ведомость сканирует конкретные слои, а этого слоя в
; её списках просто нет.
;
; ⚠️ Запас кабеля у такого конца - НОЛЬ (кабель тут не заканчивается,
; концевой заделки нет), см. LEP:GetOneEndReserve в LEP-SPAN.LSP:
; тип "TRANS" внесён в "наземный" список ЯВНО, иначе маркер молча
; получил бы 3 м как опора.
;
;=====================================================================

(setq *LEP-Layer-Transition*   "LEP-TRANSITION")
(setq *LEP-Color-Transition*   6)     ; Пурпурный (ACI) - не совпадает с зелёными GPS-кружками
(setq *LEP-Trans-Diameter*     0.5)   ; м, диаметр кружка-маркера

;; Направление смещения подписи (угол в РАДИАНАХ, 0 = вправо, против
;; часовой стрелки) - у обычной опоры всегда 45° (вверх-вправо, как
;; было и раньше). У блока МТП три опоры стоят близко друг к другу
;; (шаг 3м/2м) - если все три подписи пустить в одну и ту же сторону,
;; они накладываются друг на друга (реальная проблема, замечена
;; пользователем 2026-07-10) - поэтому у LEP-END каждая из трёх
;; подписей уходит в СВОЮ сторону (веером), см. LEP-END.LSP.
(setq *LEP-Label-Angle-Default* (/ pi 4.0))          ; 45°, вверх-вправо (обычные опоры)
(setq *LEP-End-LabelAngle-RLK*  (* 0.75 pi))         ; 135°, вверх-влево
(setq *LEP-End-LabelAngle-MTP*  (/ pi 2.0))          ; 90°, прямо вверх
(setq *LEP-End-LabelAngle-SchU* (/ pi 4.0))          ; 45°, вверх-вправо


;=====================================================================
;      КОТЛОВАНЫ ГНБ (LEP-PITSYM.LSP / LEP-SPAN.LSP) - 2026-08-11
;=====================================================================
;
; ✅ ДОБАВЛЕНО 2026-08-11 по требованию пользователя: у ЛЮБОГО
; ГНБ-прокола в реальности всегда есть два котлована - рабочий (там
; стоит буровая установка) и приёмный (там бур выходит наружу). На
; чертеже их рисовали руками; теперь они ставятся автоматически на обоих
; концах каждого проектируемого пролёта КЛ, у которого METHOD = "GNB".
;
; ⚠️ ГЛАВНЫЙ ПРИНЦИП: КОТЛОВАН - СВОЙСТВО ТОЧКИ, А НЕ ПРОЛЁТА.
; Котлован принадлежит УЗЛУ (концевому блоку - опоре, КТП, киоску,
; маркеру смены прокладки), а не отдельному проколу. Из этого одного
; правила выходят сразу все требования пользователя:
;
;   - несколько ПАРАЛЛЕЛЬНЫХ кабелей ГНБ по одной трассе висят на ТЕХ
;     ЖЕ концевых блоках (POLE1HANDLE/POLE2HANDLE у них совпадают) -
;     значит узел один, и котлован тоже один, сколько бы кабелей туда
;     ни пришло;
;   - в точке смены направления прокола (маркер TRANS) сходятся ДВА
;     прокола - но узел там опять же один, и котлован один: физически
;     буровая переставляется в тот же самый котлован.
;
; Дедупликация идёт ПО ХЕНДЛУ УЗЛА (ключ HOSTHANDLE в XDATA котлована),
; а НЕ по расстоянию между точками. Сравнение координат с допуском рано
; или поздно либо слепило бы два разных котлована в один, либо
; раздвоило бы один - и то, и другое молча, без признаков на чертеже.
;
; ⚠️ ПОДПИСЬ ОДНА НА ОБА ТИПА - "Рабочий/Приемный котлован" (решение
; пользователя 2026-08-11). Программа не знает и не может знать, с
; какой стороны прокола реально встанет буровая: это решает бурильщик
; на местности, а не геометрия чертежа. Спрашивать при каждом проколе
; пользователь отказался ("лучше без доп вопросов"), поэтому ставится
; общий текст, а лишнее слово стирается вручную при оформлении.
; Промежуточный узел (для одного прокола приёмный, для другого рабочий)
; получает подпись ОДИН РАЗ, вместе с самим котлованом - второй прокол,
; пришедший в тот же узел, не добавляет ни котлована, ни второй выноски.
;
; *LEP-Pit-Offset* - на сколько метров ЦЕНТР котлована отступает от
; точки узла ВНУТРЬ пролёта (т.е. котлованы одного прокола смотрят друг
; на друга). Зачем отступ вообще: котлован, посаженный центром прямо на
; опору, накрыл бы и её символ, и границу чужого участка - пользователь
; на своих чертежах двигал их руками именно поэтому. 2,0 м = половина
; длины котлована (1,0) плюс 1,0 м просвета от трапеции опоры, которая
; занимает примерно ±0,5 м поперёк трассы (было 1,5 м, увеличено по
; просьбе пользователя 2026-08-11 - вплотную смотрелось тесно).
;
; ⚠️ Отступ - это ЦЕЛЬ, а не гарантия: на коротком проколе он
; автоматически ужимается (см. LEP:PlacePitAtNode в LEP-SPAN.LSP),
; иначе на проколе в пару метров котлованы уехали бы за собственные
; концы. Ужатие сопровождается сообщением в консоль.
;
; ⚠️ РАЗМЕР ОДИН НА ВСЕ КОТЛОВАНЫ - 2,0 x 1,5 м (снято с чертежа
; пользователя: Area 3.0000, Length 7.0000 у замкнутой полилинии - это
; ровно стороны 2,0 и 1,5). В диалоге не спрашивается, глубина/диаметр
; прокола на размер не влияют (решение пользователя 2026-08-11).
; ДЛИНА идёт ВДОЛЬ оси прокола, ширина - поперёк.
;
; ⚠️ СЛОЙ ПЕЧАТАЕМЫЙ, в отличие от маркера TRANS: котлован - это
; элемент готового чертежа и объём земляных работ, он ДОЛЖЕН попадать в
; PDF. Вес линии - общий проектный *LEP-LWeight-Proj* (0,50 мм), а не
; 0,70 мм со скриншота: 0,70 там было у линии подосновы, а котлован
; должен чертиться той же толщиной, что и остальные проектируемые
; объекты (прямое уточнение пользователя).
;
; ⚠️ В ВЕДОМОСТЬ НЕ ИДЁТ (решение пользователя). Отдельных действий для
; этого не потребовалось - LEP-REPORT.LSP сканирует конкретные слои и
; конкретные значения TYPE, а ни слоя LEP-PIT, ни типа "PIT" в её
; списках нет.
;
;=====================================================================

(setq *LEP-Layer-Pit*      "LEP-PIT")
(setq *LEP-Color-Pit*      5)      ; Синий (ACI) - как на чертеже пользователя
(setq *LEP-Pit-Length*     2.0)    ; м, ВДОЛЬ оси прокола
(setq *LEP-Pit-Width*      1.5)    ; м, ПОПЕРЁК оси прокола
(setq *LEP-Pit-Offset*     2.0)    ; м, от точки узла внутрь пролёта до ЦЕНТРА котлована
(setq *LEP-Label-Pit*      "Рабочий/Приемный котлован")


;=====================================================================
;         GPS-ТОЧКИ ИЗ GEOJSON (LEP-GEOPOINTS.LSP) - 2026-07-20
;=====================================================================
;
; Пользователь снимает GPS-координаты опор в поле (экспорт в GeoJSON,
; WGS84 - широта/долгота), затем нужно поставить на чертёж временные
; зелёные кружки-ориентиры в ТЕХ ЖЕ координатах, что и подоснова
; (МСК-47), чтобы рядом с ними вручную расставить настоящие символы
; опор (Сущ.). Кружки - НЕ часть постоянного чертежа, только рабочий
; ориентир, поэтому отдельный непечатаемый слой (как *LEP-Layer-Route*)
; и отдельная команда его полной очистки.
;
; ⚠️ ВАЖНО - перевод координат WGS84 -> МСК-47 делается НЕ в LISP:
; своя формула (черновая полиномиальная регрессия по 25 калибровочным
; точкам одного участка) была отвергнута - у каждой зоны МСК-47 своё
; смещение и своя нелинейность, локальная подгонка не переживает
; переезд на другой участок (см. LEP-README.md, раздел про GPS-точки,
; полная история). Вместо этого пользователь считает координаты САМ
; через сайт-конвертер (подтверждён рабочим, там указан официальный
; код EPSG:6334702 - МСК-47 зона 2 Ленинградская область, не
; самодельное приближение) - LISP только читает готовый результат.
;
; *LEP-GeoPoints-Diameter* - диаметр кружка (по просьбе пользователя,
; "просто точки", 1 метр - достаточно заметно на плане, но не мешает
; рядом расставлять настоящие опоры).
;
; *LEP-GeoPoints-LabelOffset* - на сколько метров вправо от ЦЕНТРА
; кружка ставится подпись (название точки из GeoJSON) - чуть больше
; радиуса кружка (0.5 м), чтобы подпись не наезжала на сам кружок.
;
;=====================================================================

(setq *LEP-Layer-GeoPoints*         "LEP-GEOPOINTS")
(setq *LEP-Color-GeoPoints*         3)      ; Зелёный (ACI)
(setq *LEP-GeoPoints-Diameter*      1.0)    ; м
(setq *LEP-GeoPoints-LabelOffset*   0.8)    ; м, от центра кружка вправо



(princ
  (strcat
    "\n"
    "=========================================\n"
    " LEP CONFIG "
    *LEP-Version*
    " загружен.\n"
    "========================================="
  )
)

(princ)
