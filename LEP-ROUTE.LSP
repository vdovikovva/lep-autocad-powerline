;=====================================================================
;
;   ПРОЕКТ:
;   LEP
;
;   ФАЙЛ:
;   LEP-ROUTE.LSP
;
;   ВЕРСИЯ:
;   1.0  (Escape во время рисования PLINE больше не срывает создание
;        маршрута молча - цикл ожидания CMDACTIVE обёрнут в
;        vl-catch-all-apply, чтобы *error* не обрывал функцию ДО
;        проверки RouteEnt - баг найден пользователем живьём, Claude,
;        2026-07-22)
;   0.9  (подпись "Маршрут NN" переехала на слой LEP-Layer-Route -
;        не печатается, скрывается вместе с линией маршрута, Claude,
;        2026-07-15)
;   0.8  (LEP:BringToFront для подписи маршрута, Claude, 2026-07-15)
;   0.7  (защита от молчаливого срыва создания маршрута - вырожденная
;        полилиния/потерянный entlast теперь громко предупреждает,
;        баг найден пользователем при Shift+ПКМ во время PLINE -
;        Claude, 2026-07-15)
;   0.6  (LEP:CreateRouteLabel: фон под текстом выносок, Claude, 2026-07-15)
;   0.5  (LEP:CreateRouteLabel: LEADER -> MLEADER, Claude, 2026-07-15)
;   0.4  (обработчик ошибок: Esc при рисовании больше не оставляет
;   текущим служебный слой - аудит Claude Fable, 2026-07-11)
;
;   НАЗНАЧЕНИЕ:
;
;   Создание маршрута проектируемой линии.
;
;   Алгоритм:
;
;   1. Пользователь рисует трассу PLINE.
;   2. Программа спрашивает класс напряжения (10кВ/0,4кВ) - один раз
;      на весь маршрут, см. *LEP-VoltageClasses* в LEP-CONFIG.LSP.
;   3. Программа присваивает ей уникальный ID.
;   4. ID и класс напряжения записываются внутрь DWG (XDATA).
;   5. Далее к этому маршруту будут привязаны:
;
;      - опоры;
;      - пролеты;
;      - кабели;
;      - оборудование.
;
;=====================================================================



;=====================================================================
;
; КОМАНДА:
;
; LEP-ROUTE
;
;=====================================================================


;=====================================================================
;
; LEP:CreateRouteLabel
;
; Подпись "Маршрут NN" у начальной точки только что нарисованного
; маршрута - чтобы на чертеже было видно, где какой маршрут, а не
; только внутри XDATA (снаружи это раньше было никак не отличить).
; NN - последние 2 символа RouteID (сам ID теперь короткий, 2 цифры,
; см. LEP:CreateRouteID в LEP-DATA.LSP).
;
;=====================================================================

(defun LEP:CreateRouteLabel (Point RouteID / TextPoint OldLayer LabelText Num)

    (setq OldLayer (getvar "CLAYER"))

    ;; ⚠️ ФИКС 2026-07-15 (просьба пользователя): подпись "Маршрут NN" -
    ;; чисто техническая пометка, не настоящая надпись чертежа - раньше
    ;; сидела на *LEP-Layer-Text* (тот же слой, что и подписи опор/
    ;; пролётов - печатается, попадает в PDF). Теперь - на служебном
    ;; слое самого маршрута (*LEP-Layer-Route*), у которого печать
    ;; ВСЕГДА выключена (LEP:SetLayerNoPlot, LEP-SETUP.LSP) - подпись
    ;; автоматически перестаёт печататься/попадать в PDF, ничего
    ;; отдельно настраивать не нужно. Побочный эффект (ожидаемый,
    ;; обсуждён с пользователем): подпись теперь прячется/появляется
    ;; ВМЕСТЕ со служебной линией маршрута через LEP-ROUTEVIS, а не
    ;; видна всегда, как раньше - для чисто технической пометки это и
    ;; есть желаемое поведение.
    (LEP:SetCurrentLayer *LEP-Layer-Route*)

    (setq Num (substr RouteID (- (strlen RouteID) 1)))
    (setq LabelText (strcat "Маршрут " Num))

    (setq TextPoint
        (list
            (+ (car Point) *LEP-LeaderOffset*)
            (+ (cadr Point) *LEP-LeaderOffset*)
        )
    )

    ;; МИГРАЦИЯ 2026-07-15: LEADER -> MLEADER (см. LEP-CONFIG.LSP,
    ;; раздел "СТИЛЬ ВЫНОСОК MLEADER"). Вызов проще, чем у LEADER -
    ;; просто две точки и текст, без "пусто"-ответов на промежуточные
    ;; промпты.
    (command "_.MLEADER" Point TextPoint LabelText)

    ;; Фон под текстом - свойство КАЖДОЙ выноски отдельно, не стиля
    ;; (см. LEP-CONFIG.LSP, раздел "ФОНОВАЯ МАСКА ТЕКСТА ВЫНОСОК").
    (LEP:SetMLeaderBackgroundMask (entlast))

    ;; Порядок отрисовки - наверх (по просьбе пользователя 2026-07-15,
    ;; см. LEP:BringToFront, LEP-UTILS.LSP).
    (LEP:BringToFront (entlast))

    (setvar "CLAYER" OldLayer)
)


(defun C:LEP-ROUTE

    (

        /

        OldLayer

        OldError

        RouteEnt

        RouteID

        StartPt

        VClassChoice

        VClass

    )



    ;---------------------------------------------------------------
    ; Локальный обработчик ошибок (⚠️ ФИКС 2026-07-11, аудит: это
    ; была ЕДИНСТВЕННАЯ команда проекта без него). Без обработчика
    ; Esc во время рисования PLINE обрывал функцию ДО строки
    ; восстановления слоя - текущим оставался служебный слой
    ; LEP-ROUTE-SERVICE, у которого ВЫКЛЮЧЕНА ПЕЧАТЬ: всё, что
    ; пользователь начертил бы дальше руками, тихо не выходило бы
    ; на бумагу. Паттерн тот же, что в LEP-POLE/SPAN/SCALE/END.
    ;---------------------------------------------------------------

    (setq OldError *error*)
    (defun *error* (msg)
        (if OldLayer (setvar "CLAYER" OldLayer))
        (setq *error* OldError)
        (princ (strcat "\nКоманда прервана: " msg))
        (princ)
    )



    (LEP:PrintHeader

        "Создание маршрута ЛЭП"

    )



    ;---------------------------------------------------------------
    ; Запоминаем текущий слой
    ;---------------------------------------------------------------

    (setq OldLayer

        (getvar "CLAYER")

    )



    ;---------------------------------------------------------------
    ; Переключаемся на служебный слой маршрута - это НЕ ВЛ/КЛ, просто
    ; "арматура" для констрейнтов опор (см. LEP-CONFIG). Печать этого
    ; слоя всегда выключена, видимость на экране - через LEP-ROUTEVIS.
    ;---------------------------------------------------------------

    (LEP:SetCurrentLayer

        *LEP-Layer-Route*

    )


    ;---------------------------------------------------------------
    ; Создание полилинии
    ;---------------------------------------------------------------
    (princ "\nРисуйте трассу ЛЭП. После завершения нажмите Enter.")
    
    (command "_.PLINE")

    ;; ✅ ФИКС 2026-07-22 (найден пользователем живьём, см. LEP-README.md
    ;; для полной истории): цикл ожидания обёрнут в vl-catch-all-apply.
    ;; Раньше Escape ВО ВРЕМЯ рисования PLINE (уже после нескольких
    ;; поставленных точек) поднимал в AutoLISP условие "Function
    ;; cancelled" ПРЯМО внутри этого цикла - а в C:LEP-ROUTE есть свой
    ;; *error* (см. выше, фикс 2026-07-11, изначально для ДРУГОЙ цели -
    ;; не оставлять текущим служебный слой). *error* ловил это условие
    ;; и, как и положено обработчику ошибок в AutoLISP, ПОСЛЕ своей
    ;; работы завершал ВСЮ функцию ЦЕЛИКОМ - выполнение никогда не
    ;; доходило до проверки RouteEnt/entlast ниже, а значит и до
    ;; "громкого" предупреждения "МАРШРУТ НЕ СОЗДАН" (добавленного в
    ;; 2026-07-15 именно для такого случая) - оно попросту не успевало
    ;; сработать. Полилиния при этом на чертеже ОСТАВАЛАСЬ (Escape не
    ;; отменяет уже поставленные точки PLINE) - но БЕЗ XDATA
    ;; (LEP:AddRoute так и не вызывался) - опоры на ней потом получали
    ;; фиктивный ID "LEP_ROUTE_UNKNOWN" (см. C:LEP-POLE) молча, без
    ;; единого предупреждения. Теперь vl-catch-all-apply ловит "Function
    ;; cancelled" ДО того, как до него доберётся *error* (тот вообще не
    ;; вызывается) - выполнение спокойно продолжается ДАЛЬШЕ по функции,
    ;; к уже существующей проверке RouteEnt, которая теперь ДЕЙСТВИТЕЛЬНО
    ;; получает шанс сработать: создать честный маршрут с ID, если точек
    ;; было поставлено достаточно (2+), либо громко предупредить, если
    ;; нет - именно то поведение, которое и задумывалось фиксом
    ;; 2026-07-15, но которое не работало для ЭТОГО конкретного сценария
    ;; прерывания.
    (vl-catch-all-apply
        '(lambda ()
            (while (> (getvar "CMDACTIVE") 0)
                (command pause)
            )
         )
     '())

    ;; entlast - последний созданный объект В ЧЕРТЕЖЕ, а не обязательно
    ;; наша полилиния: если пользователь отменил PLINE через Esc сразу
    ;; (не поставив ни одной точки), entlast вернёт какой-то ДРУГОЙ,
    ;; уже существовавший ранее объект - и код принял бы его за
    ;; маршрут. Проверяем тип явно, а не доверяем entlast вслепую.
    (setq RouteEnt (entlast))
    (if (and RouteEnt (/= (cdr (assoc 0 (entget RouteEnt))) "LWPOLYLINE"))
        (setq RouteEnt nil)
    )

    ;; ⚠️ ФИКС 2026-07-15 (баг пользователя): временная привязка Shift+ПКМ
    ;; ("Parallel" и т.п.) во время рисования PLINE может сорвать цикл
    ;; ожидания выше так, что entlast поймает ЧУЖУЮ/вырожденную
    ;; сущность (либо не поймает вообще ничего пригодного) - раньше
    ;; это молча пропускалось (LEP:AddRoute/LEP:CreateRouteLabel просто
    ;; не вызывались), а трасса на вид оставалась нормальной полилинией,
    ;; но БЕЗ XDATA - опоры на ней потом получали фиктивный ID
    ;; "LEP_ROUTE_UNKNOWN" (см. C:LEP-POLE), а подпись маршрута не
    ;; появлялась - и то, и другое молча, без явного предупреждения.
    ;; Точный механизм срыва цикла не воспроизведён живьём - защита
    ;; ниже не пытается его угадать, а просто ловит РЕЗУЛЬТАТ (меньше
    ;; 2 вершин - не полноценная трасса) и громко предупреждает, чтобы
    ;; проблема не всплыла только в ведомости через полчаса.
    (if (and RouteEnt (< (length (LEP:GetVertices RouteEnt)) 2))
        (setq RouteEnt nil)
    )



    ;---------------------------------------------------------------
    ; Проверка результата
    ;---------------------------------------------------------------

    (if RouteEnt


        (progn



            ;-------------------------------------------------------
            ; Класс напряжения маршрута - спрашивается ОДИН РАЗ здесь,
            ; а не на каждом пролёте/опоре (в жизни напряжение не
            ; меняется посреди трассы - между 10кВ и 0,4кВ участками
            ; всегда стоит трансформатор МТП, то есть физически это
            ; уже НОВЫЙ маршрут). Дальше LEP-SPAN и LEP-POLE читают
            ; этот класс из XDATA маршрута (ключ VCLASS) - список марок
            ; провода и вторая строка подписи опоры зависят от него.
            ; Отмена (Enter без выбора) - считаем 10 кВ по умолчанию,
            ; чтобы не срывать создание маршрута из-за необязательного
            ; уточнения.
            ;-------------------------------------------------------

            (setq VClassChoice
                (LEP:ChooseFromList *LEP-VoltageClasses* "Класс напряжения маршрута")
            )
            (if VClassChoice
                (setq VClass (cdr VClassChoice))
                (setq VClass "10")
            )



            ;-------------------------------------------------------
            ; Создаем ID маршрута
            ;-------------------------------------------------------

            (setq RouteID

                (LEP:AddRoute

                    RouteEnt

                    VClass

                )

            )



            ;-------------------------------------------------------
            ; Подпись "Маршрут NN" у начальной точки - чтобы было
            ; видно на чертеже, а не только в XDATA.
            ;-------------------------------------------------------

            (setq StartPt (car (LEP:GetVertices RouteEnt)))
            (LEP:CreateRouteLabel StartPt RouteID)



            (princ

                "\nСоздан маршрут: "

            )


            (princ RouteID)

        )


        (princ
            (strcat
                "\n========================================"
                "\n[LEP-ROUTE] МАРШРУТ НЕ СОЗДАН!"
                "\nПолилиния не поймана (или получилась вырожденной -"
                "\nменьше 2 вершин). ID/класс напряжения НЕ записаны,"
                "\nподпись НЕ создана - если сейчас на экране всё же"
                "\nвидна линия, она НИЧЕЙ не имеет отношения к проекту,"
                "\nудалите её и нарисуйте маршрут заново командой"
                "\nLEP-ROUTE. Если это повторится - постарайтесь не"
                "\nделать ничего необычного (доп. привязки Shift+ПКМ и"
                "\nт.п.) во время самого рисования полилинии, только"
                "\nпосле - и сообщите, при каких именно действиях"
                "\nповторилось."
                "\n========================================"
            )
        )


    )



    ;---------------------------------------------------------------
    ; Возвращаем исходный слой и обработчик ошибок
    ;---------------------------------------------------------------

    (setvar

        "CLAYER"

        OldLayer

    )

    (setq *error* OldError)



    (LEP:PrintFooter)



    (princ)

)



;=====================================================================
;
; КОМАНДА:
;
; LEP-ROUTEVIS
;
; Быстрое включение/выключение видимости служебной линии маршрута
; (слой LEP-ROUTE-SERVICE) на экране - без похода в диспетчер слоёв,
; где в реальном чертеже их может быть много. Печать этого слоя
; всегда выключена отдельно (см. LEP-SETUP), это только про экран.
;
; Нужно ВКЛЮЧИТЬ маршрут перед тем, как кликать по нему в LEP-SPAN
; (выбор полилинии) или тянуть опору - на выключенном слое объекты
; не выбираются. Удобно ВЫКЛЮЧИТЬ его, чтобы наглядно смотреть,
; где ВЛ (сплошная), а где КЛ (штрих "К") - маршрут снизу их не
; перекрывал бы.
;
; Состояние слоя (вкл/выкл) определяется по знаку группы 62 в его
; записи в таблице LAYER: отрицательный цвет = слой выключен.
;
;=====================================================================

(defun C:LEP-ROUTEVIS (/ LayerData IsOff)

    (LEP:PrintHeader "Видимость служебной линии маршрута")

    (if (not (LEP:LayerExists *LEP-Layer-Route*))
        (princ
            (strcat
                "\nСлой " *LEP-Layer-Route* " ещё не создан - "
                "выполните LEP-SETUP или нарисуйте маршрут (LEP-ROUTE)."
            )
        )
        (progn
            (setq LayerData (tblsearch "LAYER" *LEP-Layer-Route*))
            (setq IsOff (< (cdr (assoc 62 LayerData)) 0))

            ;; Если собираемся ВЫКЛЮЧИТЬ и маршрут сейчас - текущий слой,
            ;; "-layer Off" на нём спросит подтверждение (это текущий
            ;; слой). Уводим CLAYER на "0" заранее, чтобы не залипнуть.
            (if (and (not IsOff) (= (getvar "CLAYER") *LEP-Layer-Route*))
                (setvar "CLAYER" "0")
            )

            (if IsOff
                (progn
                    (command "_.-layer" "_On" *LEP-Layer-Route* "")
                    (princ (strcat "\nМаршрут (" *LEP-Layer-Route* ") включён."))
                )
                (progn
                    (command "_.-layer" "_Off" *LEP-Layer-Route* "")
                    (princ (strcat "\nМаршрут (" *LEP-Layer-Route* ") скрыт."))
                )
            )
        )
    )

    (LEP:PrintFooter)
    (princ)
)



;=====================================================================
; C:LEP-ROUTE-CLEAN - УБОРКА ПАРАЗИТНЫХ ВЕРШИН МАРШРУТА
;
; ✅ ДОБАВЛЕНО 2026-08-20 по просьбе пользователя, вторая половина
; правки про лишние размеры (первая - LEP:CollapseDimVertices в
; LEP-SPAN.LSP).
;
; ОТКУДА БЕРУТСЯ ПАРАЗИТНЫЕ ВЕРШИНЫ. Угловая опора почти всегда
; ставится рядом с изломом, который пользователь нарисовал руками. А
; снап "это та же самая точка" в LEP:InsertVertexOnRoute -
; *LEP-Vertex-Snap-Tolerance*, ВСЕГО 10 СМ. Клик мимо излома на
; полметра - и в маршруте появляется ВТОРАЯ вершина рядом с первой.
; На живом чертеже пользователя из 26 вершин пять оказались такими
; парами (0,13-0,80 м друг от друга).
;
; ЧЕМ ОНИ МЕШАЮТ. Сами по себе - почти ничем: длина считается как
; сумма отрезков и от лишней вершины не меняется, провод рисуется по
; той же трассе. Мешают они РАЗМЕРАМ - каждый участок между вершинами
; получал свою размерную линию, и рядом с "30 м" вылезало "1 м".
; С 2026-08-20 размеры от этого защищены схлопыванием
; (LEP:CollapseDimVertices), так что эта команда - уборка ради
; порядка, а не обязательный шаг.
;
; ЧТО УДАЛЯЕТСЯ. Вершина удаляется, только если ВЫПОЛНЕНО ВСЁ:
;   - в ней НЕ стоит узловой блок (опора, КТП, киоск, маркер) -
;     проверка LEP:VertexHasNode, допуск *LEP-Dim-NodeSnap*;
;   - рядом (ближе *LEP-Dim-NodeGap*) есть другая вершина, в которой
;     блок СТОИТ - то есть это именно "лишний близнец опоры";
;   - это не первая и не последняя вершина маршрута.
; Одиночный излом трассы без опоры под ним НЕ ТРОГАЕТСЯ: это
; настоящий поворот, и размер по нему нужен.
;
; ⚠️ ГЛАВНЫЙ РИСК - GEOMCONSTRAINT. Опоры привязаны к вершинам
; маршрута связью _COincident (LEP:PlacePoleOnRoute). Мы удаляем
; только вершины БЕЗ блока, то есть заведомо не те, за которые
; кто-то держится. Но список вершин полилинии при этом перестраивается
; целиком (entmod), а как решатель ограничений AutoCAD переживает
; сдвиг индексов - живьём НЕ ПРОВЕРЕНО. Известно лишь, что обратная
; операция (вставка вершины в середину списка тем же entmod) работает
; годами - на ней держится вся расстановка опор.
;
; ПОЭТОМУ: команда спрашивает подтверждение, работает с ОДНИМ
; маршрутом за раз и прямо просит проверить после себя, не съехали ли
; опоры. Если съехали - Ctrl+Z (одна операция entmod откатывается
; целиком).
;
; ⚠️ ЧЕГО КОМАНДА НЕ ДЕЛАЕТ: не трогает уже нарисованные размеры и
; подписи. Они лежат на чертеже как есть - "уже начерченное задним
; числом не пересчитывается", общее правило проекта. Лишний размер
; "1 м" после уборки надо стереть руками (или перечертить пролёт).
;=====================================================================

(defun C:LEP-ROUTE-CLEAN (/ PickEnt Route RouteID Verts Nodes N i j Kill
                            HasNodeNear Answer NewVerts Item Data NewData
                            VIdx Skip Removed)

    (LEP:PrintHeader "Уборка лишних вершин маршрута")

    ;; Кликаем по ПРОЛЁТУ, а не по самой трассе: слой маршрутов обычно
    ;; скрыт (LEP-ROUTEVIS), а провод виден всегда. Если пользователь
    ;; всё же включил слой и кликнул по трассе - принимаем и её.
    (setq PickEnt (car (entsel "\n[LEP-ROUTE-CLEAN] Клик по пролёту нужного маршрута (или по самой трассе): ")))

    (cond

        ((not PickEnt)
            (princ "\n[LEP-ROUTE-CLEAN] Отменено.")
            (LEP:PrintFooter)
        )

        (t
            (cond
                ;; Кликнули по самой полилинии маршрута.
                ((= (LEP:GetDataValue PickEnt "TYPE") "ROUTE")
                    (setq Route PickEnt)
                    (setq RouteID (LEP:GetDataValue PickEnt "ID"))
                )
                ;; Кликнули по пролёту - берём маршрут из его XDATA.
                ((= (LEP:GetDataValue PickEnt "TYPE") "SPAN")
                    (setq RouteID (LEP:GetDataValue PickEnt "ROUTE"))
                    (setq Route (if RouteID (LEP:FindRouteByID RouteID) nil))
                )
                (t (setq Route nil))
            )

            (if (not Route)
                (progn
                    (princ "\n[LEP-ROUTE-CLEAN] Это не пролёт и не трасса - маршрут не определён.")
                    (LEP:PrintFooter)
                )
                (progn

                    (setq Verts (LEP:GetVertices Route))
                    (setq N (length Verts))
                    (setq Nodes (LEP:CollectNodePoints))

                    ;; Kill - список индексов вершин на удаление.
                    (setq Kill nil)
                    (setq i 1) ; первую не трогаем никогда

                    (while (< i (1- N))

                        (if (not (LEP:VertexHasNode (nth i Verts) Nodes))
                            (progn
                                ;; Есть ли рядом вершина, в которой блок
                                ;; РЕАЛЬНО стоит? Если да - наша лишняя.
                                (setq HasNodeNear nil)
                                (setq j 0)
                                (while (< j N)
                                    (if (and (/= j i)
                                             (< (distance (nth i Verts) (nth j Verts)) *LEP-Dim-NodeGap*)
                                             (LEP:VertexHasNode (nth j Verts) Nodes)
                                        )
                                        (setq HasNodeNear T)
                                    )
                                    (setq j (1+ j))
                                )
                                (if HasNodeNear
                                    (setq Kill (append Kill (list i)))
                                )
                            )
                        )

                        (setq i (1+ i))
                    )

                    (if (not Kill)
                        (progn
                            (princ (strcat "\n[LEP-ROUTE-CLEAN] Маршрут " (if RouteID RouteID "?")
                                           ": вершин " (itoa N) ", лишних не найдено."))
                            (LEP:PrintFooter)
                        )
                        (progn

                            (princ (strcat "\n[LEP-ROUTE-CLEAN] Маршрут " (if RouteID RouteID "?")
                                           ": вершин " (itoa N) ", из них лишних " (itoa (length Kill)) "."))
                            (foreach i Kill
                                (princ
                                    (strcat "\n  вершина " (itoa i)
                                            " - до предыдущей вершины "
                                            (rtos (distance (nth i Verts) (nth (1- i) Verts)) 2 2)
                                            " м"
                                    )
                                )
                            )
                            (princ "\n[LEP-ROUTE-CLEAN] ⚠️ Опоры привязаны к вершинам связью GEOMCONSTRAINT. После уборки ПРОВЕРЬТЕ, что опоры на месте; если съехали - Ctrl+Z.")

                            ;; ⚠️ Скобки в строке getkword - ТОЛЬКО список
                            ;; ответов, префикс отдельным princ ДО initget
                            ;; (иначе Dynamic Input покажет у курсора
                            ;; "LEP-ROUTE-CLEAN" вместо "Да"/"Нет").
                            (initget "Да Нет")
                            (setq Answer (getkword "\nУдаляем лишние вершины? [Да/Нет] <Нет>: "))

                            (if (/= Answer "Да")
                                (progn
                                    (princ "\n[LEP-ROUTE-CLEAN] Отменено, чертёж не тронут.")
                                    (LEP:PrintFooter)
                                )
                                (progn

                                    ;; Перестраиваем DXF-данные полилинии.
                                    ;;
                                    ;; ⚠️ Удалять надо не только саму группу
                                    ;; 10, но и хвост вершины - группы 40/41
                                    ;; (ширины) и 42 (bulge), которые идут
                                    ;; ПОСЛЕ неё до следующей 10. Иначе они
                                    ;; переехали бы на чужую вершину и
                                    ;; полилиния поехала бы шириной/дугой.
                                    ;; У наших трасс их обычно нет вовсе, но
                                    ;; закладываться на это нельзя: подложку
                                    ;; и трассы рисуют по-разному.
                                    (setq Data (entget Route))
                                    (setq NewData nil)
                                    (setq VIdx -1)
                                    (setq Skip nil)

                                    (foreach Item Data
                                        (cond
                                            ((= (car Item) 10)
                                                (setq VIdx (1+ VIdx))
                                                (setq Skip (if (member VIdx Kill) T nil))
                                                (if (not Skip)
                                                    (setq NewData (append NewData (list Item)))
                                                )
                                            )
                                            ((member (car Item) '(40 41 42))
                                                (if (not Skip)
                                                    (setq NewData (append NewData (list Item)))
                                                )
                                            )
                                            ((= (car Item) 90)
                                                (setq NewData
                                                    (append NewData
                                                        (list (cons 90 (- N (length Kill))))
                                                    )
                                                )
                                            )
                                            (t (setq NewData (append NewData (list Item))))
                                        )
                                    )

                                    (entmod NewData)
                                    (entupd Route)

                                    (setq Removed (length Kill))
                                    (princ (strcat "\n[LEP-ROUTE-CLEAN] Удалено вершин: " (itoa Removed)
                                                   ", осталось " (itoa (- N Removed)) "."))
                                    (princ "\n[LEP-ROUTE-CLEAN] ⚠️ Уже нарисованные размеры и подписи НЕ пересчитаны - лишний размер сотрите руками или перечертите пролёт.")
                                    (LEP:PrintFooter)
                                )
                            )
                        )
                    )
                )
            )
        )
    )

    (princ)
)


(princ "\nLEP-ROUTE v1.1 загружен (Escape во время PLINE больше не срывает создание маршрута молча; LEP-ROUTE-CLEAN).")

(princ)
