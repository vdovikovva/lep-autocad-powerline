;=====================================================================
;
;   ПРОЕКТ:      LEP
;   ФАЙЛ:        LEP-KKSYM.LSP
;   ВЕРСИЯ:      0.1  (первая версия - Claude, 2026-07-24)
;
;   НАЗНАЧЕНИЕ:
;   Символ КК - кабельного киоска (*LEP-KK-Width* x *LEP-KK-Height*,
;   LEP-CONFIG.LSP). ПРОСТОЙ ПРЯМОУГОЛЬНИК, БЕЗ значка внутри - в
;   отличие от КТП (LEP-KTPSYM.LSP), у которой внутри треугольник-
;   трансформатор. Так решил пользователь 2026-07-24: в киоске
;   трансформатора нет, рисовать внутри нечего, там только приборы
;   учёта, а они на плане никак не показываются (учитываются числом,
;   см. ключ PUCOUNT в XDATA киоска).
;
;   ЗАЧЕМ ПОНАДОБИЛСЯ (реальный случай пользователя 2026-07-24):
;   из КТП выходят два кабеля 0,4 кВ и идут к участку заявителя, где
;   НЕТ ни опор, ни МТП - стоит просто кабельный киоск с двумя
;   приборами учёта. До этого дня закончить кабель в проекте было
;   нечем, кроме опоры.
;
;   УСТРОЕН ПО ОБРАЗЦУ LEP-KTPSYM.LSP - тот же принцип, что и у символа
;   опоры (LEP-POLESYM.LSP): блок создаётся ОДИН РАЗ через entmake
;   (BLOCK/LWPOLYLINE/ENDBLK), дальше вставляется через entmake
;   (INSERT) - не через интерактивные "-BLOCK"/"-INSERT" (надёжнее, нет
;   риска нарваться на диалог или неверный порядок промптов, см.
;   правило про `command` в CLAUDE.md).
;
;   ⚠️ Блок, как и символы опоры/КТП, создаётся ТОЛЬКО ЕСЛИ ЕЩЁ НЕ
;   СУЩЕСТВУЕТ - НЕ передефайнится при повторной загрузке. Если
;   понадобится поправить геометрию (например уточнить размер - сейчас
;   1х2 м это ПРИКИДКА, как было у КТП с 3х5) после того, как на
;   чертеже уже стоят киоски - см. README, раздел про символ опоры,
;   там общее решение этой проблемы.
;
;=====================================================================

(setq *LEP-Block-Kk* "LEP-KK-SYM")


;=====================================================================
; LEP:CreateKkSymbolBlock
;
; Создаёт блок-символ кабельного киоска (*LEP-Block-Kk*) - один
; прямоугольник. Точка вставки блока (0,0,0) - геометрический центр
; прямоугольника (тот же принцип, что у символов опоры и КТП).
;=====================================================================

(defun LEP:CreateKkSymbolBlock (/ HalfW HalfH RectVerts RectList V)

    (if (not (tblsearch "BLOCK" *LEP-Block-Kk*))
        (progn
            (setq HalfW (/ *LEP-KK-Width* 2.0))
            (setq HalfH (/ *LEP-KK-Height* 2.0))

            (entmake
                (list
                    (cons 0 "BLOCK")
                    (cons 2 *LEP-Block-Kk*)
                    (cons 70 0)
                    (cons 10 (list 0.0 0.0 0.0))
                    (cons 8 "0")
                )
            )

            ;; Прямоугольник - закрытая LWPOLYLINE (группа 70 = 1),
            ;; LWEIGHT = ByBlock (группа 370 = -2): толщина линии
            ;; наследуется от самого INSERT, чтобы её можно было задать
            ;; по статусу Проект./Сущ. снаружи - тот же приём, что у
            ;; трапеции опоры и у прямоугольника КТП.
            (setq RectVerts
                (list
                    (list (- HalfW) (- HalfH))
                    (list HalfW (- HalfH))
                    (list HalfW HalfH)
                    (list (- HalfW) HalfH)
                )
            )
            (setq RectList
                (list
                    '(0 . "LWPOLYLINE")
                    '(100 . "AcDbEntity")
                    (cons 8 "0")
                    (cons 370 -2)
                    '(100 . "AcDbPolyline")
                    (cons 90 (length RectVerts))
                    '(70 . 1)
                )
            )
            (foreach V RectVerts
                (setq RectList (append RectList (list (cons 10 V))))
            )
            (entmake RectList)

            (entmake (list (cons 0 "ENDBLK") (cons 8 "0")))

            (princ (strcat "\n[LEP-KKSYM] Создан блок-символ кабельного киоска: " *LEP-Block-Kk*))
        )
    )
)


;=====================================================================
; LEP:InsertKkSymbol
;
; Вставляет символ киоска в точку Point, слой - по статусу
; (*LEP-Layer-Proj-TP*/*LEP-Layer-Exist-TP*, ТЕ ЖЕ слои, что и у КТП -
; отдельный слой для киоска заводить не стали, ведомость различает их
; по ключу TYPE в XDATA, а не по слою, см. ЭТАП 2.6 в LEP-REPORT.LSP).
;
; Без разворота (группа 50 всегда 0) - киоск, как и КТП, не
; привязывается к направлению маршрута, в отличие от символа опоры.
;
; Возвращает ename вставленного блока - вызывающая сторона
; (LEP-END.LSP) использует его для GEOMCONSTRAINT и XDATA
; (LEP:AddKkData).
;=====================================================================

(defun LEP:InsertKkSymbol (Point Status / Layer)

    (if (= Status "EXIST")
        (setq Layer *LEP-Layer-Exist-TP*)
        (setq Layer *LEP-Layer-Proj-TP*)
    )

    (entmake
        (list
            '(0 . "INSERT")
            (cons 8 Layer)
            (cons 2 *LEP-Block-Kk*)
            (cons 10 (list (car Point) (cadr Point) 0.0))
            (cons 41 1.0)
            (cons 42 1.0)
            (cons 43 1.0)
            (cons 50 0.0)
        )
    )

    ;; Толщина линии по статусу (Проект. жирнее Сущ.) - те же общая
    ;; функция и константы, что у опор и КТП. Работает именно потому,
    ;; что прямоугольник внутри блока имеет LWEIGHT = ByBlock (см.
    ;; LEP:CreateKkSymbolBlock выше).
    (if (= Status "EXIST")
        (LEP:SetEntityLWeight (entlast) *LEP-LWeight-Exist*)
        (LEP:SetEntityLWeight (entlast) *LEP-LWeight-Proj*)
    )

    (entlast)
)


(princ "\nLEP-KKSYM v0.1 загружен (символ кабельного киоска - прямоугольник).")
(princ)
