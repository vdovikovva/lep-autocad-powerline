;=====================================================================
; ПРОЕКТ:       LEP (Автоматизация проектирования ЛЭП)
; ФАЙЛ:         LEP-SCALE.LSP
; ВЕРСИЯ:       0.3  (правки по итогам теста - Claude)
; НАЗНАЧЕНИЕ:   Калибровка растровой подложки (скана, карты, кадастра).
;               Приводит чертеж к масштабу 1 единица = 1 метр
;               на основе графической масштабной линейки.
;
; ПРАВКИ В ЭТОЙ ВЕРСИИ: после калибровки подложка принудительно
; перекладывается на слой KADASTR (могла оказаться на другом - см.
; LEP-SETUP.LSP, "-LAYER Make" оставляет текущим последний созданный
; слой) и отправляется в конец порядка отрисовки (DRAWORDER "_Back"),
; чтобы линии маршрута/опор поверх неё не "проваливались" под неё
; визуально.
;=====================================================================

(defun C:LEP-SCALE ( / ImgEnt P1 P2 MeasDist InputVal RealDist OldOs OldError RefKeywords RefPrompt L )

    ;-----------------------------------------------------------------
    ; ЛОКАЛЬНЫЙ ОБРАБОТЧИК ОШИБОК
    ; Предотвращает поломку настроек AutoCAD при аварийном нажатии ESC
    ;-----------------------------------------------------------------
    (setq OldError *error*) ; Запоминаем стандартный обработчик ошибок
    (defun *error* (msg)
        (if OldOs (setvar "OSMODE" OldOs)) ; Гарантированно возвращаем привязки
        (setq *error* OldError)            ; Восстанавливаем обработчик
        (princ (strcat "\n[LEP-SCALE] Команда прервана: " msg))
        (princ)
    )

    ; Выводим фирменную шапку проекта из LEP-UTILS
    (LEP:PrintHeader "Калибровка масштаба подложки")
    
    ;-----------------------------------------------------------------
    ; ШАГ 1: ВЫБОР ОБЪЕКТА ПОДЛОЖКИ
    ;-----------------------------------------------------------------
    ; entsel приостанавливает выполнение и ждет клика по объекту.
    ; Возвращает список: (ename (координаты клика)). Нам нужен только ename -> car.
    (setq ImgEnt (car (entsel "\nВыберите изображение подложки (карту/кадастр): ")))
    
    (if ImgEnt
        (progn
            ; Временная деактивация объектных привязок (OSMODE = 0).
            ; Это критично: при клике по картинке курсор не должен магнититься 
            ; к случайным векторам геометрии, лежащим рядом.
            (setq OldOs (getvar "OSMODE"))
            (setvar "OSMODE" 0)

            ;---------------------------------------------------------
            ; ШАГ 2: ФИКСАЦИЯ ОПОРНЫХ ТОЧЕК НА КАРТЕ
            ;---------------------------------------------------------
            ; getpoint запрашивает координаты. Передача точки P1 во второй вызов
            ; включает "резиновый канат" (визуальную линию связи) от P1 к курсору.
            (setq P1 (getpoint "\nУкажите ПЕРВУЮ точку на масштабной линейке карты: "))
            (setq P2 (getpoint P1 "\nУкажите ВТОРУЮ точку на масштабной линейке карты: "))
            
            ; Возвращаем привязки инженеру сразу после сбора графических данных
            (setvar "OSMODE" OldOs)
            (setq OldOs nil) ; Обнуляем переменную, чтобы *error* её не трогал

            ; Вычисляем текущее расстояние в абстрактных единицах AutoCAD
            (setq MeasDist (distance P1 P2))
            (princ (strcat "\nИзмеренная длина в чертеже: " (rtos MeasDist 2 4) " ед."))
            
            ;---------------------------------------------------------
            ; ШАГ 3: ИНТЕРАКТИВНЫЙ ЗАПРОС РЕАЛЬНОЙ ДЛИНЫ
            ;---------------------------------------------------------
            ; Механика initget + getreal:
            ; Строка вида "10 20 50 100" задаёт жёсткие макросы-ключи для
            ; быстрого ввода. Строится ДИНАМИЧЕСКИ из *LEP-ReferenceLengths*
            ; в LEP-CONFIG.LSP (раньше эти же числа были захардкожены прямо
            ; тут же текстом, а конфиг-переменная лежала неиспользуемая -
            ; правило проекта "все магические числа только в CONFIG", см.
            ; шапку LEP-CONFIG.LSP, нарушалось; теперь список меняется в
            ; одном месте - в CONFIG).
            ; Если инженер введёт одно из этих чисел или выберет в контекстном
            ; меню, getreal вернёт это значение как СТРОКУ (например, "50").
            ; Если инженер введёт ЛЮБОЕ ДРУГОЕ число (например, 25), getreal
            ; поймёт, что это свободный ввод, и вернёт ЧИСЛО типа REAL (25.0).
            (setq RefKeywords "")
            (setq RefPrompt "")
            (foreach L *LEP-ReferenceLengths*
                (setq RefKeywords (strcat RefKeywords (if (= RefKeywords "") "" " ") (rtos L 2 0)))
                (setq RefPrompt (strcat RefPrompt (if (= RefPrompt "") "" "/") (rtos L 2 0)))
            )
            (initget RefKeywords)
            (setq InputVal (getreal (strcat "\nВведите реальное расстояние в метрах [" RefPrompt "] или укажите своё: ")))
            
            ; Анализируем тип возвращенного значения для предотвращения сбоя типизации
            (cond
                ; Вариант А: Пользователь выбрал ключ из initget -> пришла строка
                ((= (type InputVal) 'STR)
                    (setq RealDist (atof InputVal)) ; Парсим строку в вещественное число
                )
                ; Вариант Б: Пользователь ввел свое уникальное число -> пришло число
                ((= (type InputVal) 'REAL)
                    (setq RealDist InputVal)
                )
                ; Вариант В: Пользователь нажал Enter без ввода (отмена)
                (t (setq RealDist nil))
            )
            
            ;---------------------------------------------------------
            ; ШАГ 4: МАТЕМАТИЧЕСКОЕ МАСШТАБИРОВАНИЕ ОБЪЕКТА
            ;---------------------------------------------------------
            ; Проверяем валидность полученного значения
            (if (and RealDist (> RealDist 0.0))
                (progn
                    ; Вызов встроенной команды SCALE через командный интерфейс AutoCAD.
                    ; Механика Опции Ссылка (_Reference):
                    ; Исходная длина (MeasDist) заменяется Новой длиной (RealDist).
                    ; Использование префиксов "_." и "_" гарантирует корректный запуск
                    ; команды на любых языковых версиях AutoCAD и на macOS.
                    (command "_.SCALE"
                             ImgEnt             ; Выбираем наш объект
                             ""                 ; Нажимаем Enter для завершения выбора объектов
                             P1                 ; Базовая точка масштабирования (останется на месте)
                             "_Reference"       ; Включаем режим масштабирования по ссылке
                             MeasDist           ; Передаем старый размер
                             RealDist           ; Передаем новый целевой размер в метрах
                    )

                    ;-------------------------------------------------
                    ; ШАГ 5: СЛОЙ И ПОРЯДОК ОТРИСОВКИ ПОДЛОЖКИ
                    ;-------------------------------------------------
                    ; Найдено на практике: подложка после IMAGEATTACH
                    ; иногда оказывается не на слое KADASTR, а на том,
                    ; что был текущим в момент вставки (например,
                    ; LEP-DIM - LEP-SETUP оставляет его текущим, т.к.
                    ; команда "-LAYER Make" делает текущим каждый
                    ; только что созданный слой, а LEP-DIM создаётся
                    ; последним по списку). LEP-SCALE - последний шаг
                    ; перед тем, как поверх подложки начинают чертить,
                    ; поэтому именно здесь принудительно перекладываем
                    ; её на правильный слой - независимо от того, на
                    ; каком слое она оказалась изначально.
                    (entmod
                        (subst
                            (cons 8 *LEP-Layer-Kadastr*)
                            (assoc 8 (entget ImgEnt))
                            (entget ImgEnt)
                        )
                    )

                    ; Растровые изображения в AutoCAD по умолчанию
                    ; отрисовываются ПОВЕРХ векторной геометрии
                    ; независимо от порядка создания - маршрут,
                    ; начерченный поверх подложки, зрительно "проваливался"
                    ; под неё. DRAWORDER "_Back" отправляет подложку в
                    ; самый низ порядка отрисовки, чтобы линии поверх
                    ; неё оставались видны всегда, что бы ни рисовали
                    ; потом (маршрут, опоры, пролёты).
                    (command "_.draworder" ImgEnt "" "_Back")

                    ; Печать лога калибровки для инженерного контроля
                    (princ "\n==========================================")
                    (princ (strcat "\n[УСПЕХ] Масштаб подложки откалиброван."))
                    (princ (strcat "\n Пропорция: " (rtos MeasDist 2 2) " ед. -> превращены в " (rtos RealDist 2 2) " м."))
                    (princ "\n Теперь 1 единица чертежа строго равна 1 метру.")
                    (princ "\n==========================================")
                )
                (princ "\n[ОТМЕНА] Калибровка не выполнена: некорректное расстояние.")
            )
        )
        (princ "\n[ОШИБКА] Объект подложки не выбран.")
    )
    
    ; Восстанавливаем стандартную систему обработки ошибок AutoCAD
    (setq *error* OldError)
    (LEP:PrintFooter)
    (princ)
)

;; Информируем консоль о штатной загрузке модуля
(princ "\nМодуль LEP-SCALE v0.3 успешно загружен (слой+draworder подложки после калибровки).")
(princ)
