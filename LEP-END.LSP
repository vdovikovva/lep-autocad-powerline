;=====================================================================
;
;   ПРОЕКТ:      LEP
;   ФАЙЛ:        LEP-END.LSP
;   ВЕРСИЯ:      1.5  (2026-08-11: ВИДЫ приборов учёта. Два пункта меню
;                ("ПУ" и "ПУ на существующую опору") слиты в один -
;                "ПУ на опору"; опору он БОЛЬШЕ НЕ СОЗДАЁТ, её ставят
;                заранее командой LEP-POLE. Спрашивается ВИД ПУ
;                (*LEP-PU-Types*), в XDATA/ведомость уходит строка
;                спецификации целиком, на выноску - короткая метка
;                (LEP:GetPuShortLabel). Вид спрашивается и у приборов
;                внутри кабельного киоска (*LEP-PU-Types-KK*, ключ
;                PUTYPE). Статус самого прибора всегда "Проект.";
;                слово "проект." в подписи пишется ТОЛЬКО на
;                существующей опоре - Claude)
;   1.4  (2026-08-03: у окончания "ПУ" СВОЙ тип опоры -
;                *LEP-End-PoleType-PU* ("П23"), у СТП и трёх опор МТП
;                прежний *LEP-End-PoleType* ("П20-3Н"). Тип считается
;                один раз в переменную PoleType и используется везде -
;                блок, подпись, XDATA. В ведомость попадает сам собой:
;                ЭТАП 2 читает тип из ключа MODEL, а "П23" есть в
;                справочнике *LEP-PoleStands* - Claude)
;   1.3  (2026-08-03: пункт "Точка смены способа прокладки
;                КЛ" переименован в "Точка разрыва участка КЛ (смена
;                способа ИЛИ новый прокол)" - маркер ставится и там, где
;                способ НЕ меняется: два прокола ГНБ подряд под разными
;                углами это ДВА прокола. Сама логика маркера не
;                тронута, изменилось поведение объединения подписей -
;                см. LEP-SPAN.LSP 2.1 - Claude)
;   1.2  (2026-07-28: все ветки команды запоминают ename
;                созданной подписи и передают его в LEP:AddEquipData -
;                без этого опоры ПУ/СТП/РЛК/МТП/ЩУ оставались без
;                LABELHANDLE: к опоре с ПУ не дописывалось "+ подъём
;                кабеля по опоре" (LEP:AddKLPoleNote), а LEP-POLE-DELETE
;                не убирал их подпись - Claude)
;   1.1  (2026-07-24: МТП на 6 кВ - две новые строки в
;                *LEP-MTP-Types* ("МТП-160/6/0,4"/"МТП-250/6/0,4"),
;                всё остальное общее с 10 кВ (геометрия, подписи РЛК/ЩУ,
;                слой, статус). Новая LEP:GetDefaultMtpLabel - фолбэк
;                на Enter больше не подставляет жёстко 10 кВ на
;                6-киловольтном маршруте - Claude)
;   1.0  (2026-07-22: КТП - новый пункт меню, наземная
;                подстанция БЕЗ опоры, свой блок-символ (LEP-KTPSYM.LSP,
;                прямоугольник+треугольник ОДНИМ объектом - переделано
;                из двух независимых объектов по прямой правке
;                пользователя после показанного скриншота, заодно
;                треугольник растянут на всю высоту прямоугольника),
;                номер/мощность/марка - свободный ввод, три строки
;                подписи; учтена в ведомости (ЭТАП 2.6, LEP-REPORT.LSP) -
;                Claude)
;   0.9  (2026-07-22: СТП - новый пункт меню, одна опора +
;                "+ СТП-XX кВА" второй строкой (как ПУ, текстом, без
;                отдельной графики - пока); подпись МТП теперь
;                указывает на середину между 2-й и 3-й опорой (там
;                физически висит трансформатор), а не на саму опору 2 -
;                Claude)
;   0.8  (LEP:InsertPole получил VClass - слой опоры по
;                классу напряжения, см. LEP-POLE.LSP/LEP-CONFIG.LSP -
;                Claude, 2026-07-22)
;   0.7  (выбор мощности МТП - *LEP-MTP-Types*, Claude,
;                2026-07-16)
;   0.6  (третий пункт "ПУ на существующую опору" - без
;                новой геометрии, дописывает строку в готовую подпись,
;                Claude, 2026-07-15)
;   0.5  (статус Сущ./Проект. для оконечного оборудования +
;                фикс направления МТП с любого конца маршрута -
;                Claude, 2026-07-15)
;   0.4  (фикс направления опор МТП + одна концовка за
;                запуск - аудит Claude Fable, 2026-07-11)
;
;   ИСПРАВЛЕНО В ЭТОЙ ВЕРСИИ:
;
;   1. ⚠️ ГЕОМЕТРИЯ: опоры 2 (МТП) и 3 (ЩУ) смещались от первой опоры
;      по углу Rotation - а это угол ПОВОРОТА БЛОКА (= угол маршрута
;      МИНУС 90°, см. LEP:GetPoleRotation) - т.е. блок МТП уезжал
;      ПЕРПЕНДИКУЛЯРНО трассе, а не продолжал её, как описывал
;      пользователь ("через 3 метра вторая, ещё через 2 третья").
;      Проверено тригонометрией: cos(θ-90°)=sin θ, sin(θ-90°)=-cos θ -
;      скалярное произведение с направлением трассы равно нулю, чистый
;      перпендикуляр. Сами трапеции при этом СМОТРЕЛИ правильно
;      (поворот блока считается отдельно), поэтому в куче наложенных
;      подписей на тесте это было легко не заметить. Теперь смещение
;      считается по углу САМОГО МАРШРУТА (RouteDir), поворот блока -
;      по-прежнему по Rotation. Это два разных угла, отличаются на 90°.
;
;   2. Команда ставит ОДНУ концовку и завершается - убран цикл while
;      (по прямой просьбе пользователя 2026-07-10: "после вставки
;      оконечного блока надо закрывать команду... если надо - я ещё
;      раз запущу"; правка тогда потерялась за разбирательствами с
;      отступом LEADER, восстановлена при аудите).
;
;   НАЗНАЧЕНИЕ:
;   Оконечное оборудование маршрута - то, чем заканчивается трасса
;   ЛЭП у заявителя (см. присланные пользователем скриншоты реальных
;   чертежей, 2026-07-10):
;
;     ПУ  (0,4 кВ, мелкий заявитель)  - ⚠️ 2026-08-11: НИКАКОЙ
;                                        геометрии. Прибор учёта
;                                        навешивается на УЖЕ СТОЯЩУЮ
;                                        опору (её ставят командой
;                                        LEP-POLE, тип "П23"): строка
;                                        дописывается в её подпись,
;                                        вид прибора - в её XDATA.
;                                        Промах мимо опоры не рисует
;                                        ничего. Раньше этот пункт сам
;                                        ставил опору, а рядом жил
;                                        второй пункт "ПУ на
;                                        существующую опору" - их
;                                        объединили.
;     МТП (10 или 6 кВ,               - 3 опоры *LEP-End-PoleType*
;          крупный заявитель)            подряд (шаг *LEP-End-MTP-
;                                        Spacing1*/-Spacing2* м),
;                                        подписи РЛК / МТП-160/10/0,4 /
;                                        ЩУ, разведённые в разные
;                                        стороны (*LEP-End-LabelAngle-*),
;                                        чтобы не накладывались.
;                                        Мощность И класс высокой
;                                        стороны выбираются из списка
;                                        *LEP-MTP-Types* (2026-07-24
;                                        туда добавлены варианты 6 кВ -
;                                        от 10 кВ отличается ТОЛЬКО
;                                        строка подписи, вся геометрия
;                                        и всё остальное общее).
;
;   РЛК/МТП/ЩУ/ПУ - НЕ отдельная графика, только текстовые подписи
;   рядом с опорой (подтверждено пользователем - реальные чертежи
;   показывают именно так, без отдельных значков).
;
;   Первая опора группы (РЛК для МТП, единственная для СТП) ставится
;   ТАК ЖЕ, как в LEP-POLE - проекция клика на ближайший отрезок
;   маршрута, вставка новой вершины, привязка GEOMCONSTRAINT - это
;   прямое продолжение трассы. Остальные опоры блока МТП (2-я и 3-я)
;   НЕ проецируются на маршрут - вставляются дальше по направлению
;   трассы (за пределами нарисованной полилинии).
;
;   Тип опоры для МТП/СТП ЗАФИКСИРОВАН (не спрашивается) - по прямому
;   указанию пользователя, общий *LEP-End-PoleType* ("П20-3Н").
;   ⚠️ 2026-08-11: у ПУ своего типа больше нет - опору под него эта
;   команда не ставит вовсе (см. выше), тип выбирается руками в
;   LEP-POLE. С 2026-08-03 по 2026-08-11 у ПУ был свой
;   *LEP-End-PoleType-PU* ("П23"), константа осталась в конфиге на
;   случай отката. Тип берётся один раз в переменную PoleType, дальше
;   по всей команде используется только она - и при вставке блока, и в
;   подписи, и в XDATA (иначе они могли бы разойтись, а на чертеже это
;   не видно).
;
;   ⚠️ ФИКС 2026-07-15: статус (Проект./Сущ.) раньше был зашит намертво
;   ("существующего МТП/ПУ не бывает") - оказалось, бывает: иногда
;   нужно начертить УЖЕ СУЩЕСТВУЮЩЕЕ оконечное оборудование (например
;   при подключении к уже стоящей подстанции), а не только то, что
;   проектируется - иначе оно попадало бы в ведомость проектируемых
;   материалов как новое. Теперь статус спрашивается ОДИН раз на весь
;   блок (как и тип ПУ/МТП) - LEP:GetStatus, та же общая функция,
;   что и у обычных опор в LEP-POLE.LSP.
;
;   ⚠️ ФИКС 2026-07-15: опоры 2/3 блока МТП (были ПУ - тут только
;   одна опора, вопрос не встаёт) раньше уезжали ДАЛЬШЕ ПО RouteDir
;   БЕЗУСЛОВНО - а RouteDir это направление ЛОКАЛЬНОГО отрезка трассы
;   под точкой клика (от его начала к концу), не "куда от маршрута
;   наружу". Если ставить МТП у ПОСЛЕДНЕЙ вершины маршрута - это
;   работало верно (опоры уезжали за пределы линии). Если у ПЕРВОЙ
;   вершины - RouteDir "смотрел" вдоль маршрута ВНУТРЬ, и опоры 2/3
;   налезали на уже нарисованную трассу и её опоры. Теперь направление
;   разворачивается на 180°, если точка установки ближе к ПЕРВОЙ
;   вершине маршрута, чем к ПОСЛЕДНЕЙ (сравнение расстояний через
;   LEP:GetVertices) - блок МТП теперь всегда уезжает НАРУЖУ от
;   маршрута, с какого конца трассы его ни ставь.
;
;   ⚠️ ДОБАВЛЕНО 2026-07-15, ПЕРЕДЕЛАНО 2026-08-11: пункт "ПУ на
;   существующую опору" появился по просьбе пользователя ("не плодить
;   новую опору ради ПУ, если подключение реально идёт к уже стоящей",
;   и "команд и так хоть жопой жуй" - не заводить отдельную команду).
;   С 2026-08-11 он ЕДИНСТВЕННЫЙ путь для ПУ и называется просто "ПУ на
;   опору": НИКАКОЙ новой геометрии не создаётся (ни трапеции, ни
;   вершины, ни GEOMCONSTRAINT) - только дописывается строка в подпись
;   уже стоящей опоры (LEP:AppendMLeaderText, LEP-UTILS.LSP - подпись
;   находится по хендлу LABELHANDLE в её собственной XDATA) и
;   записываются данные для ведомости (LEP:AddEquipToExistingPole,
;   LEP-DATA.LSP - НЕ обычная LEP:AddEquipData, та стёрла бы XDATA
;   опоры целиком).
;
;   Опора при этом может быть ЛЮБОЙ - и существующей, и проектируемой:
;   в ведомость она попадает по СВОЕМУ собственному STATUS, а прибор -
;   отдельной строкой по EQUIP. Ведомость смотрит оба слоя опор: ЭТАП 2
;   (проектируемые) и ЭТАП 2.5 (существующие) в LEP-REPORT.LSP.
;
;   ⚠️ 2026-08-11: ВИД прибора учёта (сплит / полукос / не уточнён)
;   спрашивается ДО клика и уходит в EQUIP ПОЛНОЙ СТРОКОЙ спецификации,
;   а на выноску - КОРОТКОЙ меткой (LEP:GetPuShortLabel). Это два
;   РАЗНЫХ текста, и так задумано: закупщику в CSV нужна полная
;   формулировка, а подписи опор и так двух-трёхстрочные.
;
;=====================================================================



;=====================================================================
; LEP:GetDefaultMtpLabel
;
; Название МТП "по умолчанию" - что подставить, если пользователь
; нажал Enter вместо выбора мощности из списка (*LEP-MTP-Types*).
;
; ✅ ДОБАВЛЕНО 2026-07-24 вместе с появлением МТП на 6 кВ. Раньше здесь
; стояла жёсткая константа *LEP-Label-MTP* ("МТП-160/10/0,4") - и пока
; МТП были только 10-киловольтные, это было безобидно. С появлением
; 6 кВ это стало МИНОЙ: на 6-киловольтном маршруте случайный Enter
; молча поставил бы МТП на 10 кВ, и она ушла бы в ведомость отдельной
; НЕВЕРНОЙ строкой (название МТП пишется в XDATA целиком, см.
; *LEP-MTP-Types* в LEP-CONFIG.LSP).
;
; Как ищем: берём ПЕРВУЮ строку из *LEP-MTP-Types*, у которой высокая
; сторона совпадает с классом маршрута. Формат строки - "мощность/ВН/
; НН" ("МТП-160/6/0,4"), поэтому ищем подстроку "/6/" - со слэшами с
; обеих сторон, иначе "/6/" случайно нашлось бы внутри другого числа.
; Так решение переживёт добавление новых мощностей и новых классов
; напряжения без правки этой функции.
;
; Если совпадения нет (класс маршрута 0,4 кВ - МТП там не ставят; или
; старый маршрут вообще без VCLASS) - откатываемся на прежнюю
; константу *LEP-Label-MTP*. Ничего не ломается, поведение как раньше.
;
; ⚠️ Это НЕ фильтрация списка: в самом списке по-прежнему показываются
; ВСЕ варианты (прямое решение пользователя 2026-07-24, см.
; LEP-CONFIG.LSP). Здесь мы правим только то, что подставляется, когда
; пользователь НЕ выбрал ничего.
;=====================================================================

(defun LEP:GetDefaultMtpLabel (VClass / Needle Found Item)

    (setq Found nil)

    (if VClass
        (progn
            (setq Needle (strcat "/" VClass "/"))
            (foreach Item *LEP-MTP-Types*
                (if (and (not Found)
                         (vl-string-search Needle (cdr Item))
                    )
                    (setq Found (cdr Item))
                )
            )
        )
    )

    (if Found Found *LEP-Label-MTP*)
)


;=====================================================================
; LEP:GetPuShortLabel
;
; Что писать НА ЧЕРТЕЖЕ для выбранного вида ПУ (2026-08-11).
;
; ⚠️ Строка спецификации (уходит в XDATA и в ведомость) и подпись на
; выноске - РАЗНЫЕ строки, сознательно: подписи опор и так
; двух-трёхстрочные, полная формулировка вида "ПУ сплит прямого
; включения" полезла бы на соседние объекты, а закупщику в CSV нужна
; как раз она целиком. Таблица перевода - *LEP-PU-ShortLabels*
; (LEP-CONFIG.LSP).
;
; Вида нет в таблице (например его дописали в *LEP-PU-Types*, а сюда
; внести забыли) - возвращаем строку спецификации КАК ЕСТЬ. Подпись
; получится длинной и это сразу видно глазом - в отличие от варианта
; "вернуть общее ПУ", который тихо соврал бы на чертеже.
;=====================================================================

(defun LEP:GetPuShortLabel (PuSpec / Found)
    (setq Found (assoc PuSpec *LEP-PU-ShortLabels*))
    (if Found (cdr Found) PuSpec)
)


;=====================================================================
; LEP:AskPuType
;
; Спросить вид прибора учёта (2026-08-11) - общая функция для ПУ на
; опоре и для ПУ внутри кабельного киоска: списки у них разные
; (*LEP-PU-Types* / *LEP-PU-Types-KK*, см. LEP-CONFIG.LSP), а логика
; одна.
;
; Enter (отказ от выбора) - НЕ обрыв команды, а возврат к прежнему
; поведению: общая строка "ПУ" (*LEP-Label-PU*). Ровно тот же принцип,
; что у мощности МТП и высокой стороны КТП - пропущенное уточнение не
; должно стоить пользователю всей постановки объекта.
;
; ⚠️ Пока формулировки не согласованы с коллегой (*LEP-PU-Draft* = T в
; LEP-CONFIG.LSP), каждый выбор печатает предупреждение в консоль: эти
; строки уходят в CSV заказчику ДОСЛОВНО, и человек должен видеть, что
; текст пока черновой. Согласуем - флаг в nil, код не трогаем.
;=====================================================================

(defun LEP:AskPuType (TypeList PromptText / Choice PuSpec)

    (setq Choice (LEP:ChooseFromList TypeList PromptText))
    (setq PuSpec (if Choice (cdr Choice) *LEP-Label-PU*))

    (if *LEP-PU-Draft*
        (princ
            (strcat
                "\n[LEP-END] ⚠️ Формулировка \"" PuSpec
                "\" в ведомости ЧЕРНОВАЯ (не согласована). Перед выдачей CSV заказчику - сверить со списком *LEP-PU-Types* в LEP-CONFIG.LSP."
            )
        )
    )

    PuSpec
)


;=====================================================================
; LEP:CreateKtpLabel
;
; Подпись-выноска КТП (2026-07-22) - ТРИ строки, формат по референсу
; пользователя: "[статус]. КТП-[номер]" / "[мощность]/[класс маршрута]/
; 0,4 кВ" / "[марка трансформатора]" (номер/мощность/марка - свободный
; ввод, см. C:LEP-END). НЕ переиспользует LEP:CreatePoleLabel - у той
; первая строка жёстко "оп. [тип]", здесь другой формат ("КТП-...").
;=====================================================================

(defun LEP:CreateKtpLabel (Point Status Number Power HighSide Marka / StatusText Line1 Line2 LabelText TextPoint OldLayer LabelEnt)

    ;; ⚠️ ФИКС 2026-07-24 (баг найден пользователем на живом чертеже).
    ;; Этих двух строк тут НЕ БЫЛО с самого появления КТП (2026-07-22):
    ;; команда "_.MLEADER" рисует на ТЕКУЩЕМ слое, какой бы он ни был,
    ;; а подписи опор и пролётов (LEP:CreatePoleLabel/LEP:CreateSpanLabel)
    ;; текущий слой честно переключают - здесь про это забыли. Баг
    ;; долго не всплывал случайно: после загрузки текущим слоем
    ;; оказывался безобидный LEP-MANUAL, и подпись выглядела нормально.
    ;; Вылез он только когда в проекте появился новый слой (см.
    ;; C:LEP-SETUP - там же и системная половина этого фикса).
    (setq OldLayer (getvar "CLAYER"))
    (LEP:SetCurrentLayer *LEP-Layer-Text*)

    (if (= Status "EXIST")
        (setq StatusText "Сущ.")
        (setq StatusText "Проект.")
    )

    (setq Line1 (strcat StatusText " КТП-" Number))

    ;; ⚠️ ФИКС 2026-07-24: раньше в середину строки подставлялся КЛАСС
    ;; МАРШРУТА, на котором стоит КТП - и пока КТП ставили только на
    ;; 10-кВ трассу, это случайно совпадало с высокой стороной. Но КТП -
    ;; это ГРАНИЦА двух классов (вход 10/6 кВ, выход 0,4 кВ), и трасса
    ;; от неё к заявителю вполне может быть 0,4 кВ (реальный случай
    ;; пользователя: КТП -> два кабеля 0,4 кВ -> кабельный киоск). На
    ;; такой трассе получался мусор "160/04/0,4 кВ": и сырой код класса
    ;; вместо человекочитаемого "0,4", и логически неверно. Теперь
    ;; высокая сторона - ОТДЕЛЬНЫЙ вопрос при постановке КТП
    ;; (*LEP-KTP-HighSide*), к классу этой трассы отношения не имеет.
    (setq Line2 (strcat (rtos Power 2 0) "/" HighSide "/0,4 кВ"))

    (setq LabelText (strcat Line1 "\\P" Line2 "\\P" Marka))

    (setq TextPoint
        (list
            (+ (car Point) *LEP-LeaderOffset*)
            (+ (cadr Point) *LEP-LeaderOffset*)
        )
    )

    (command "_.MLEADER" Point TextPoint LabelText)
    (setq LabelEnt (entlast))

    (LEP:SetMLeaderBackgroundMask LabelEnt)
    (LEP:BringToFront LabelEnt)

    (setvar "CLAYER" OldLayer)

    LabelEnt
)


;=====================================================================
; LEP:CreateKkLabel
;
; Подпись-выноска кабельного киоска (КК, 2026-07-24) - ДВЕ строки:
;   "[статус]. КК-[номер]"  (или просто "[статус]. КК", если номер не
;                            указан - не у каждого киоска он есть)
;   "ПУ - N шт."            (сколько приборов учёта внутри; строка
;                            вообще не появляется, если N = 0)
;
; ⚠️ 2026-08-11 добавлен пятый аргумент PuShort - КОРОТКАЯ метка вида
; приборов учёта ("ПУ полукос"), она и печатается вместо общего "ПУ".
; Полная строка спецификации на чертеж НЕ идёт - она длинная и полезла
; бы на соседние объекты, её место в XDATA и в ведомости.
;
; Отдельная функция, а не LEP:CreatePoleLabel/LEP:CreateKtpLabel - у
; тех свой жёсткий формат первой строки ("оп. [тип]" / "КТП-[номер]").
;=====================================================================

(defun LEP:CreateKkLabel (Point Status Number PuCount PuShort / StatusText Line1 LabelText TextPoint OldLayer LabelEnt)

    ;; ⚠️ Текущий слой - см. подробное объяснение в LEP:CreateKtpLabel
    ;; выше: "_.MLEADER" рисует на текущем слое, поэтому его надо
    ;; переключить явно и вернуть обратно в конце. Именно на подписи
    ;; киоска пользователь этот баг и поймал 2026-07-24 (подпись легла
    ;; на непечатаемый слой маркеров и не попала бы в PDF).
    (setq OldLayer (getvar "CLAYER"))
    (LEP:SetCurrentLayer *LEP-Layer-Text*)

    (if (= Status "EXIST")
        (setq StatusText "Сущ.")
        (setq StatusText "Проект.")
    )

    ;; Номер может быть пустой строкой - тогда не лепим висящий дефис.
    (if (and Number (/= Number ""))
        (setq Line1 (strcat StatusText " " *LEP-Label-KK* "-" Number))
        (setq Line1 (strcat StatusText " " *LEP-Label-KK*))
    )

    ;; ⚠️ 2026-08-11: вместо общего *LEP-Label-PU* тут теперь КОРОТКАЯ
    ;; метка выбранного вида ("ПУ полукос"), её считает LEP:GetPuShortLabel
    ;; на стороне вызывающего. Страховка на nil - на случай вызова из
    ;; старого кода, который про пятый аргумент ещё не знает.
    (if (not PuShort) (setq PuShort *LEP-Label-PU*))

    (if (> PuCount 0)
        (setq LabelText (strcat Line1 "\\P" PuShort " - " (itoa PuCount) " шт."))
        (setq LabelText Line1)
    )

    (setq TextPoint
        (list
            (+ (car Point) *LEP-LeaderOffset*)
            (+ (cadr Point) *LEP-LeaderOffset*)
        )
    )

    (command "_.MLEADER" Point TextPoint LabelText)
    (setq LabelEnt (entlast))

    (LEP:SetMLeaderBackgroundMask LabelEnt)
    (LEP:BringToFront LabelEnt)

    (setvar "CLAYER" OldLayer)

    LabelEnt
)


;=====================================================================
; C:LEP-END - основная команда
;
; ОДНА концовка за запуск (без цикла): выбор типа (ПУ/МТП) -> клик
; точки рядом с концом маршрута -> установка опоры(опор) с подписями
; и данными для ведомости -> команда завершается. Нужна ещё концовка
; (крайне редкий случай) - просто запустить LEP-END снова.
;=====================================================================

(defun C:LEP-END (/ Route RouteID VClass Choice EndType Status ClickPoint InsertResult
                    Pt1 Pt2 Pt3 MtpMidPt Rotation RouteDir RouteVerts Ent1 Ent2 Ent3 OldOs OldError
                    ExistPoleEnt LabelHandle LabelEnt MtpChoice MtpLabel StpChoice StpLabel
                    KtpNumber KtpPower KtpMarka KtpHighChoice KtpHighSide
                    KkNumber KkPuCount KkPuType PoleType
                    PuSpec PuShort OldEquip Answer)

    (setq OldError *error*)
    (defun *error* (msg)
        (if OldOs (setvar "OSMODE" OldOs))
        (setq *error* OldError)
        (princ (strcat "\nКоманда прервана: " msg))
        (princ)
    )

    (LEP:PrintHeader "Оконечное оборудование маршрута (МТП / ПУ)")

    (setq OldOs (getvar "OSMODE"))
    (setvar "OSMODE" 0)

    ;; ⚠️ ФИКС 2026-07-15: выбор типа теперь ПЕРВЫМ вопросом (раньше
    ;; сначала спрашивали маршрут) - у нового пункта "ПУ на
    ;; существующую опору" маршрут вообще не нужен (RouteID берётся из
    ;; XDATA самой существующей опоры), незачем заставлять выбирать
    ;; полилинию заранее, если она не понадобится.
    (setq Choice
        (LEP:ChooseFromList
            (list
                ;; ⚠️ ОБЪЕДИНЕНО 2026-08-11 (решение пользователя): раньше
                ;; здесь было ДВА пункта - "ПУ (0,4 кВ - 1 опора)", который
                ;; сам ставил новую опору П23, и "ПУ на СУЩЕСТВУЮЩУЮ опору",
                ;; который только дописывал строку в подпись уже стоящей.
                ;;
                ;; Различались они НЕ статусом опоры (это и сбивало с толку:
                ;; второй пункт прекрасно работал и по ПРОЕКТИРУЕМОЙ опоре -
                ;; проверялся только TYPE = "POLE"), а тем, создаётся ли
                ;; опора. Пользователю это различие не нужно: "нам без
                ;; разницы, проект или сущ - она либо уже посчитана, либо
                ;; нет", и посчитана она по своему собственному STATUS,
                ;; независимо от ПУ на ней.
                ;;
                ;; Теперь пункт ОДИН и опору он НЕ СОЗДАЁТ вообще: клик по
                ;; опоре - навешиваем прибор, промах - ничего не рисуем и
                ;; говорим об этом в консоль. Опора ставится заранее обычной
                ;; командой LEP-POLE (тип "П23" есть в *LEP-PoleTypes*).
                ;; Стало на шаг длиннее, зато ПУ окончательно стал тем, чем
                ;; он и является физически - оборудованием НА опоре, а не
                ;; отдельным видом окончания трассы.
                (cons "ПУ на опору (существующую или проектируемую)" "PU")
                (cons "МТП (10/6 кВ - 3 опоры: РЛК/МТП/ЩУ)" "MTP")
                (cons "СТП (трансформатор на ОДНОЙ опоре)" "STP")
                (cons "КТП (наземная подстанция, без опоры)" "KTP")
                (cons "КК (кабельный киоск с ПУ, без опоры)" "KK")
                ;; ⚠️ ПЕРЕИМЕНОВАНО 2026-08-03. Было "Точка смены
                ;; способа прокладки КЛ (ГНБ <-> траншея)" - название
                ;; описывало ЕДИНСТВЕННЫЙ случай, ради которого маркер
                ;; заводили, и прямо отговаривало ставить его там, где
                ;; способ НЕ меняется. А ставить надо: два прокола ГНБ
                ;; подряд под разными углами - это ДВА разных прокола
                ;; (бур вышел из земли и зашёл заново), им нужны свои
                ;; подписи и свой счёт труб, и разделяет их именно этот
                ;; маркер. Теперь название говорит про общий смысл -
                ;; "здесь один участок работ кончился, начался другой".
                (cons "Точка разрыва участка КЛ (смена способа ИЛИ новый прокол)" "TRANS")
            )
            ;; ⚠️ Формулировка запроса поменялась 2026-07-24 с "Тип
            ;; оконечного оборудования" на нейтральную: точка смены
            ;; способа прокладки - НЕ оконечное оборудование, она стоит
            ;; посреди трассы. Отдельную команду ради неё не заводили
            ;; (пользователь ещё в июле: "команд и так хватает"), а вся
            ;; нужная механика - проекция клика на трассу, вставка
            ;; вершины, GEOMCONSTRAINT - уже живёт именно здесь.
            "Что ставим на маршрут (Enter - отмена)"
        )
    )

    (if Choice
        (progn

            (setq EndType (cdr Choice))

            ;; ⚠️ 2026-08-11: тип опоры снова ОДИН на все окончания.
            ;; С 2026-08-03 по 2026-08-11 у "ПУ" был свой тип
            ;; (*LEP-End-PoleType-PU*, "П23") - но теперь пункт "ПУ"
            ;; опору вообще не создаёт (см. комментарий в меню выше),
            ;; и выбирать тип ему не для чего. Опоры здесь ставят
            ;; только МТП (три штуки) и СТП (одна), у них тип общий.
            ;;
            ;; Переменная (а не константа по месту) остаётся сознательно:
            ;; тип используется в трёх местах - вставка блока, подпись и
            ;; XDATA, и подставлять его в каждое место отдельно опасно.
            ;; Забытое место даёт "на чертеже одно, в подписи другое, в
            ;; CSV третье", а глазами такое расхождение не видно.
            (setq PoleType *LEP-End-PoleType*)

            (if (= EndType "PU")

                ;;-------------------------------------------------------
                ;; ПУ НА ОПОРУ - НИКАКОЙ новой геометрии (2026-08-11,
                ;; объединение двух прежних пунктов меню, см. комментарий
                ;; в самом меню выше).
                ;;
                ;; Опора должна УЖЕ СТОЯТЬ - её ставят обычной командой
                ;; LEP-POLE. Промах мимо опоры НИЧЕГО не рисует (прямое
                ;; решение пользователя): молча поставить опору там, куда
                ;; человек не целился, хуже, чем попросить его повторить
                ;; клик.
                ;;
                ;; Статус САМОГО ПРИБОРА всегда "Проект." (решение
                ;; пользователя 2026-08-11): ПУ, который мы сейчас ставим,
                ;; ставится по этому проекту - других причин рисовать его
                ;; нет. Статус ОПОРЫ при этом не трогается вообще, он свой
                ;; собственный, и именно по нему опора попадает или не
                ;; попадает в ведомость как материал.
                ;;-------------------------------------------------------

                (progn

                    ;; Вид ПУ спрашиваем ДО клика: если человек передумает
                    ;; на вопросе, он ещё ничего не успел выбрать на
                    ;; чертеже. Обратный порядок заставлял бы кликать
                    ;; впустую.
                    (setq PuSpec (LEP:AskPuType *LEP-PU-Types* "Вид прибора учёта"))
                    (setq PuShort (LEP:GetPuShortLabel PuSpec))

                    (setq ExistPoleEnt (car (entsel "\nКликните по ОПОРЕ, на которую ставится ПУ: ")))

                    (if (and ExistPoleEnt
                             (= (cdr (assoc 0 (entget ExistPoleEnt))) "INSERT")
                             (= (LEP:GetDataValue ExistPoleEnt "TYPE") "POLE")
                        )
                        (progn
                            (setq LabelHandle (LEP:GetDataValue ExistPoleEnt "LABELHANDLE"))
                            (if LabelHandle (setq LabelEnt (handent LabelHandle)))

                            ;; ⚠️ ДОБАВЛЕНО 2026-08-11: опора МОЖЕТ УЖЕ
                            ;; НЕСТИ оборудование - и это не обязательно
                            ;; ПУ: ключ EQUIP у опор МТП хранит "RLK" /
                            ;; "МТП-160/10/0,4" / "ЩУ". Запись поверх
                            ;; СТИРАЕТ прежнее значение (в XDATA ключ
                            ;; один), то есть неаккуратный клик по опоре
                            ;; РЛК молча превратил бы её в опору с ПУ, а
                            ;; РЛК пропал бы из ведомости.
                            ;;
                            ;; Раньше этой проверки не было - и это сходило
                            ;; с рук, потому что пункт назывался "ПУ на
                            ;; СУЩЕСТВУЮЩУЮ опору" и по опорам МТП по нему
                            ;; никто не кликал. Теперь пункт общий, кликать
                            ;; будут чаще, и подстраховка нужна.
                            ;;
                            ;; ⚠️ Скобки в строке запроса: единственная
                            ;; группа [] - это СПИСОК ОТВЕТОВ, иначе
                            ;; Dynamic Input подставит в подсказку у
                            ;; курсора не то (см. CLAUDE.md). Пояснение -
                            ;; отдельным princ ДО initget.
                            (setq OldEquip (LEP:GetDataValue ExistPoleEnt "EQUIP"))
                            (if OldEquip
                                (progn
                                    (princ
                                        (strcat
                                            "\n[LEP-END] ⚠️ На этой опоре УЖЕ записано оборудование: \""
                                            OldEquip "\". Запись ПУ его ЗАМЕНИТ - из ведомости оно пропадёт."
                                        )
                                    )
                                    (initget "Да Нет")
                                    (setq Answer (getkword "\nЗаменить [Да/Нет] <Нет>: "))
                                    (if (not Answer) (setq Answer "Нет"))
                                )
                                (setq Answer "Да")
                            )

                            (cond

                                ((/= Answer "Да")
                                    (princ "\n[LEP-END] Отменено - опора не тронута.")
                                )

                                ((not LabelEnt)
                                    (princ "\n[LEP-END] У этой опоры не найдена подпись (LABELHANDLE) - не могу дописать текст. Опора поставлена не через LEP-POLE?")
                                )

                                (t
                                    (progn
                                        ;; Дописываем строку в ЕЁ ЖЕ подпись -
                                        ;; не создаём отдельную выноску (см.
                                        ;; LEP:AppendMLeaderText, LEP-UTILS.LSP,
                                        ;; проверено живым тестом 2026-07-15).
                                        ;;
                                        ;; ⚠️ 2026-08-11: слово "проект." пишем
                                        ;; ТОЛЬКО на существующей опоре. У
                                        ;; проектируемой первая строка подписи и
                                        ;; так начинается с "Проект. оп. ...", и
                                        ;; "+ проект. ПУ" второй строкой читалось
                                        ;; бы как заикание. Статус берём из XDATA
                                        ;; самой опоры - ровно та мысль
                                        ;; пользователя, что "сущ. или проект.
                                        ;; определяется по опоре".
                                        (if (= (LEP:GetDataValue ExistPoleEnt "STATUS") "EXIST")
                                            (LEP:AppendMLeaderText LabelEnt (strcat "+ проект. " PuShort))
                                            (LEP:AppendMLeaderText LabelEnt (strcat "+ " PuShort))
                                        )

                                        ;; Данные для ведомости - НЕ через
                                        ;; LEP:AddEquipData (та перезаписала бы
                                        ;; XDATA опоры целиком, стерев её
                                        ;; LABELHANDLE и подменив её собственный
                                        ;; STATUS) - см. LEP:AddEquipToExistingPole,
                                        ;; LEP-DATA.LSP.
                                        ;;
                                        ;; ⚠️ 2026-08-11: в EQUIP уходит СТРОКА
                                        ;; СПЕЦИФИКАЦИИ ЦЕЛИКОМ ("ПУ полукос"), а
                                        ;; не код "PU". Тот же приём, что у МТП
                                        ;; (см. *LEP-MTP-Types*): вычислять
                                        ;; название заново при выгрузке нельзя -
                                        ;; разные виды ПУ схлопнулись бы в одну
                                        ;; строку ведомости. Старые опоры с кодом
                                        ;; "PU" продолжают работать - их переводит
                                        ;; LEP:GetEquipLabel (LEP-REPORT.LSP).
                                        (LEP:AddEquipToExistingPole ExistPoleEnt PuSpec "PROJECT")

                                        (princ (strcat "\n[LEP-END] На опору добавлен " PuSpec "."))
                                    )
                                )
                            )
                        )
                        (princ "\n[LEP-END] Это не опора (возможно, откос, наземный объект или посторонний блок). Опора должна УЖЕ СТОЯТЬ - поставьте её командой LEP-POLE (тип П23), потом запустите LEP-END снова и кликните по её ГЛАВНОЙ трапеции.")
                    )
                )

                ;;-------------------------------------------------------
                ;; ПУ-НОВАЯ / МТП - прежнее поведение, нужен маршрут.
                ;;-------------------------------------------------------

                (progn
                    (setq Route (car (entsel "\nВыберите полилинию маршрута (если не видна - включите LEP-ROUTEVIS): ")))

                    (if Route
                        (progn

                            (setq RouteID (LEP:GetDataValue Route "ID"))
                            (if (not RouteID) (setq RouteID "LEP_ROUTE_UNKNOWN"))

                            ;; ✅ ДОБАВЛЕНО 2026-07-22: класс напряжения маршрута -
                            ;; нужен LEP:InsertPole ниже, чтобы выбрать нужный из
                            ;; 4 granular слоёв опор (см. LEP-CONFIG.LSP/LEP-POLE.LSP).
                            (setq VClass (LEP:GetDataValue Route "VCLASS"))

                            ;; Статус - ОДИН раз на весь блок (как и тип), см.
                            ;; ФИКС 2026-07-15 в шапке файла - существующее
                            ;; оконечное оборудование тоже бывает.
                            ;;
                            ;; ⚠️ 2026-07-24: у точки смены способа прокладки
                            ;; статус НЕ спрашивается - она не бывает
                            ;; "проектируемой" или "существующей" (это вообще
                            ;; не материал, а граница двух видов работ), и
                            ;; лишний вопрос там был бы бессмысленным. Значение
                            ;; всё же выставляем, чтобы дальше по коду не ловить
                            ;; nil в общих ветках.
                            (if (= EndType "TRANS")
                                (setq Status "PROJECT")
                                (setq Status (LEP:GetStatus "оконечного оборудования"))
                            )

                            ;; ⚠️ ДОБАВЛЕНО 2026-07-16: выбор мощности МТП -
                            ;; только для МТП, ПУ такого выбора не требует.
                            ;; Enter (отмена выбора) - используем значение по
                            ;; умолчанию (*LEP-Label-MTP*), не обрываем всю
                            ;; постановку МТП из-за пропущенного уточнения.
                            (if (= EndType "MTP")
                                (progn
                                    (setq MtpChoice (LEP:ChooseFromList *LEP-MTP-Types* "Тип МТП (мощность/ВН/НН)"))
                                    (setq MtpLabel
                                        (if MtpChoice
                                            (cdr MtpChoice)
                                            (LEP:GetDefaultMtpLabel VClass)
                                        )
                                    )
                                )
                            )

                            ;; ✅ ДОБАВЛЕНО 2026-07-22: выбор мощности СТП - только для
                            ;; СТП, аналогично мощности МТП выше.
                            (if (= EndType "STP")
                                (progn
                                    (setq StpChoice (LEP:ChooseFromList *LEP-STP-Types* "Мощность СТП"))
                                    (setq StpLabel (if StpChoice (cdr StpChoice) (car (car *LEP-STP-Types*))))
                                )
                            )

                            ;; ✅ ДОБАВЛЕНО 2026-07-22: данные КТП - СВОБОДНЫЙ ввод
                            ;; (номер/мощность/марка), фиксированного списка нет
                            ;; (в отличие от МТП/СТП выше) - пользователь: "нет
                            ;; живых примеров из жизни чтоб допилить" список.
                            (if (= EndType "KTP")
                                (progn
                                    (setq KtpNumber (getstring T "\nНомер КТП (например 5766): "))
                                    (initget 6) ; запрет нуля и отрицательных
                                    (setq KtpPower (getreal "\nМощность КТП, кВА: "))

                                    ;; ⚠️ ДОБАВЛЕНО 2026-07-24: высокая сторона -
                                    ;; ОТДЕЛЬНЫЙ вопрос, а не класс маршрута (см.
                                    ;; подробное обоснование в LEP:CreateKtpLabel
                                    ;; выше). Enter - берём первый пункт списка
                                    ;; (10 кВ, самый частый), а не обрываем всю
                                    ;; постановку КТП из-за пропущенного уточнения -
                                    ;; тот же принцип, что у мощности МТП.
                                    (setq KtpHighChoice (LEP:ChooseFromList *LEP-KTP-HighSide* "Высокая сторона КТП"))
                                    (setq KtpHighSide
                                        (if KtpHighChoice
                                            (cdr KtpHighChoice)
                                            (cdr (car *LEP-KTP-HighSide*))
                                        )
                                    )

                                    (setq KtpMarka (getstring T "\nМарка трансформатора (например ТМГ-160): "))
                                )
                            )

                            ;; ✅ ДОБАВЛЕНО 2026-07-24: данные кабельного киоска.
                            ;; Номер - свободный ввод и может быть ПУСТЫМ (не у
                            ;; каждого киоска он есть на плане), поэтому здесь нет
                            ;; никакой проверки на пустоту - LEP:CreateKkLabel сама
                            ;; умеет собрать подпись без номера.
                            ;; Количество ПУ - initget 4 запрещает отрицательные, но
                            ;; РАЗРЕШАЕТ ноль: киоск без приборов учёта (например
                            ;; только распределительный) - вполне реальная вещь.
                            ;; Enter (nil) трактуем как 0, чтобы не уронить itoa ниже.
                            ;; ⚠️ ДОБАВЛЕНО 2026-08-11: ВИД приборов учёта в
                            ;; киоске - свой список (*LEP-PU-Types-KK*), не тот,
                            ;; что у ПУ на опоре: сплита в киоске не бывает.
                            ;; Вид ОДИН на весь киоск (решение принято
                            ;; сознательно): киоск со ВПЕРЕМЕШКУ стоящими
                            ;; приборами разных видов теоретически возможен, но
                            ;; живых примеров пока нет, а ради него пришлось бы
                            ;; спрашивать вид и количество в цикле. Понадобится -
                            ;; добавим ключи PU2TYPE/PU2COUNT, ломать ничего не
                            ;; придётся.
                            ;; Вопрос задаём ТОЛЬКО если приборы вообще есть -
                            ;; киоск без учёта (чисто распределительный) реален,
                            ;; и спрашивать про вид нуля приборов незачем.
                            (if (= EndType "KK")
                                (progn
                                    (setq KkNumber (getstring T "\nНомер киоска (Enter - без номера): "))
                                    (initget 4) ; запрет отрицательных, ноль разрешён
                                    (setq KkPuCount (getint "\nСколько приборов учёта (ПУ) в киоске: "))
                                    (if (not KkPuCount) (setq KkPuCount 0))
                                    (if (> KkPuCount 0)
                                        (setq KkPuType (LEP:AskPuType *LEP-PU-Types-KK* "Вид приборов учёта в киоске"))
                                        (setq KkPuType *LEP-Label-PU*)
                                    )
                                )
                            )

                            (setq ClickPoint (getpoint "\nТочка установки (рядом с концом трассы): "))

                            (if ClickPoint
                                (progn

                                    ;; Первая опора - как в LEP-POLE: проекция клика на
                                    ;; ближайший отрезок маршрута + новая вершина.
                                    ;; Заодно получаем отрезок трассы под точкой - из
                                    ;; него считаются ДВА РАЗНЫХ угла (см. фикс №1 в
                                    ;; шапке файла, их уже один раз перепутали):
                                    ;;   Rotation - угол ПОВОРОТА БЛОКА (маршрут - 90°),
                                    ;;              им разворачиваются трапеции;
                                    ;;   RouteDir - угол САМОГО МАРШРУТА, по нему
                                    ;;              смещаются опоры 2/3 блока МТП.
                                    (setq InsertResult (LEP:InsertVertexOnRoute Route ClickPoint))
                                    (setq Pt1 (car InsertResult))
                                    (setq Rotation (LEP:GetPoleRotation (cadr InsertResult) (caddr InsertResult)))
                                    (setq RouteDir (angle (cadr InsertResult) (caddr InsertResult)))

                                    ;; ФИКС 2026-07-15 (см. шапку файла): RouteDir
                                    ;; выше - направление ЛОКАЛЬНОГО отрезка, не
                                    ;; "наружу от маршрута". Если Pt1 ближе к
                                    ;; ПЕРВОЙ вершине маршрута, чем к ПОСЛЕДНЕЙ -
                                    ;; разворачиваем на 180°, чтобы опоры 2/3
                                    ;; блока МТП всегда уезжали наружу, а не в
                                    ;; тело уже нарисованной трассы.
                                    (setq RouteVerts (LEP:GetVertices Route))
                                    (if (< (distance Pt1 (car RouteVerts)) (distance Pt1 (last RouteVerts)))
                                        (setq RouteDir (+ RouteDir pi))
                                    )

                                    ;; ✅ ДОБАВЛЕНО 2026-07-22: КТП - НЕ опора, свой
                                    ;; блок-символ (прямоугольник+треугольник ОДНИМ
                                    ;; объектом, см. LEP-KTPSYM.LSP) вместо трапеции.
                                    ;; Rotation для неё не используется (символ КТП
                                    ;; не разворачивается по направлению маршрута).
                                    ;; ✅ 2026-07-24: киоск (КК) вставляется тем же
                                    ;; способом, что и КТП - свой блок-символ вместо
                                    ;; трапеции опоры, Rotation не используется
                                    ;; (наземные объекты не разворачиваются по
                                    ;; направлению маршрута).
                                    (cond
                                        ((= EndType "KTP")
                                            (setq Ent1 (LEP:InsertKtpSymbol Pt1 Status))
                                        )
                                        ((= EndType "KK")
                                            (setq Ent1 (LEP:InsertKkSymbol Pt1 Status))
                                        )
                                        ((= EndType "TRANS")
                                            (setq Ent1 (LEP:InsertTransSymbol Pt1))
                                        )
                                        (t
                                            (setq Ent1 (LEP:InsertPole Pt1 Rotation PoleType Status VClass))
                                        )
                                    )
                                    (command "_.GEOMCONSTRAINT" "_COincident" Ent1 Pt1 Route Pt1 "")

                                    ;; ⚠️ Страховка (см. LEP-POLE.LSP) - пустой (command)
                                    ;; закрывает GEOMCONSTRAINT, если он завис после
                                    ;; неудачной попытки наложить связь, чтобы не
                                    ;; портить остаток команды (опоры 2/3, подписи).
                                    (command)

                                    ;; ⚠️ 2026-08-11: ветка ((= EndType "PU") ...),
                                    ;; которая СТАВИЛА ОПОРУ под прибор учёта, здесь
                                    ;; удалена - весь путь "PU" теперь уходит в
                                    ;; отдельную ветку в начале команды и до этого
                                    ;; места вообще не доходит (см. комментарий в
                                    ;; меню). Опору под ПУ ставят командой LEP-POLE.
                                    ;;
                                    ;; ⚠️ Историческая справка на случай отката:
                                    ;; та ветка делала ровно две вещи -
                                    ;;   (LEP:CreatePoleLabel Pt1 PoleType Status
                                    ;;    *LEP-Label-PU* *LEP-Label-Angle-Default*)
                                    ;; и (LEP:AddEquipData Ent1 RouteID PoleType "PU"
                                    ;;    Status LabelEnt),
                                    ;; то есть была близнецом ветки СТП ниже, только
                                    ;; с типом опоры *LEP-End-PoleType-PU*.
                                    (cond

                                        ;; ✅ ДОБАВЛЕНО 2026-07-22: СТП - трансформатор на ОДНОЙ
                                        ;; опоре (не 3, как МТП). Опора ставится ТЕМ ЖЕ способом,
                                        ;; что и ПУ выше (Ent1 уже вставлен) - подпись как у
                                        ;; обычной опоры + вторая строка "+ СТП-XX кВА"
                                        ;; (ClassLabel-параметр LEP:CreatePoleLabel - тот же
                                        ;; механизм, что обычно несёт класс напряжения маршрута,
                                        ;; здесь вместо него - мощность СТП, по прямой просьбе
                                        ;; пользователя). Данные для ведомости - StpLabel целиком
                                        ;; в EQUIP, тем же приёмом, что и у МТП (разные мощности -
                                        ;; разные строки в ведомости).
                                        ((= EndType "STP")
                                            (progn
                                                (setq LabelEnt (LEP:CreatePoleLabel Pt1 PoleType Status (strcat "+ " StpLabel) *LEP-Label-Angle-Default*))
                                                (LEP:AddEquipData Ent1 RouteID PoleType StpLabel Status LabelEnt)
                                                (princ "\n[LEP-END] Установлена опора со СТП.")
                                            )
                                        )

                                        ;; ✅ ДОБАВЛЕНО 2026-07-22: КТП - наземная подстанция,
                                        ;; Ent1 сейчас - её блок-символ (не опора), см. ветку
                                        ;; выше, где он вставлен через LEP:InsertKtpSymbol
                                        ;; (LEP-KTPSYM.LSP).
                                        ((= EndType "KTP")
                                            (progn
                                                (LEP:CreateKtpLabel Pt1 Status KtpNumber KtpPower KtpHighSide KtpMarka)
                                                (LEP:AddKtpData Ent1 RouteID Status KtpNumber KtpPower KtpMarka KtpHighSide)
                                                (princ "\n[LEP-END] Установлена КТП.")
                                            )
                                        )

                                        ;; ✅ ДОБАВЛЕНО 2026-07-24: кабельный киоск.
                                        ;; Ent1 сейчас - его блок-символ (простой
                                        ;; прямоугольник, LEP-KKSYM.LSP), см. cond
                                        ;; выше. Приборы учёта внутри киоска
                                        ;; отдельными объектами НЕ рисуются - только
                                        ;; число (см. LEP:AddKkData, LEP-DATA.LSP).
                                        ;; ✅ ДОБАВЛЕНО 2026-07-24: точка смены способа
                                        ;; прокладки. Самая короткая ветка во всей
                                        ;; команде, и так и задумано: ни подписи (она
                                        ;; полезла бы в PDF, а слой маркера специально
                                        ;; непечатаемый), ни данных для ведомости
                                        ;; (маркер - не материал). Дальше пользователь
                                        ;; просто чертит ДВА пролёта: от начала трассы
                                        ;; до маркера одним способом, от маркера
                                        ;; дальше - другим.
                                        ((= EndType "TRANS")
                                            (progn
                                                (LEP:AddTransData Ent1 RouteID)
                                                (princ "\n[LEP-END] Поставлена точка разрыва участка КЛ. Теперь начертите ДВА пролёта: до неё и от неё - они получат РАЗНЫЕ подписи и посчитаются как два отдельных участка.")
                                            )
                                        )

                                        ((= EndType "KK")
                                            (progn
                                                ;; ⚠️ 2026-08-11: подписи и данным киоска
                                                ;; добавлен ВИД приборов учёта. На чертеже -
                                                ;; короткая метка ("ПУ полукос - 2 шт."), в
                                                ;; XDATA (ключ PUTYPE) - полная строка
                                                ;; спецификации, оттуда её берёт ведомость.
                                                (LEP:CreateKkLabel Pt1 Status KkNumber KkPuCount (LEP:GetPuShortLabel KkPuType))
                                                (LEP:AddKkData Ent1 RouteID Status KkNumber (itoa KkPuCount) KkPuType)
                                                (princ
                                                    (strcat
                                                        "\n[LEP-END] Установлен кабельный киоск (ПУ внутри: "
                                                        (itoa KkPuCount) " шт.)."
                                                    )
                                                )
                                            )
                                        )

                                        (t
                                            (progn
                                                ;; Опора 1 (уже вставлена выше) - РЛК. Три
                                                ;; подписи блока МТП разведены в РАЗНЫЕ
                                                ;; стороны (веером) - опоры стоят близко
                                                ;; друг к другу (шаг 3м/2м), при одинаковом
                                                ;; направлении подписи накладывались друг на
                                                ;; друга (замечено пользователем на тесте).
                                                (setq LabelEnt (LEP:CreatePoleLabel Pt1 PoleType Status *LEP-Label-RLK* *LEP-End-LabelAngle-RLK*))
                                                (LEP:AddEquipData Ent1 RouteID PoleType "RLK" Status LabelEnt)

                                                ;; Опора 2 (место подвеса МТП) - дальше ПО
                                                ;; НАПРАВЛЕНИЮ МАРШРУТА (RouteDir, НЕ Rotation -
                                                ;; см. фикс №1 в шапке файла) на
                                                ;; *LEP-End-MTP-Spacing1* м. НЕ проекция на
                                                ;; маршрут - это уже за пределами нарисованной
                                                ;; полилинии.
                                                (setq Pt2
                                                    (list
                                                        (+ (car Pt1) (* *LEP-End-MTP-Spacing1* (cos RouteDir)))
                                                        (+ (cadr Pt1) (* *LEP-End-MTP-Spacing1* (sin RouteDir)))
                                                    )
                                                )
                                                (setq Ent2 (LEP:InsertPole Pt2 Rotation PoleType Status VClass))

                                                ;; Опора 3 (ЩУ) - ещё дальше по маршруту на
                                                ;; *LEP-End-MTP-Spacing2* м от опоры 2. Считаем
                                                ;; ДО подписи МТП (ниже) - нужна её точка для
                                                ;; середины.
                                                (setq Pt3
                                                    (list
                                                        (+ (car Pt2) (* *LEP-End-MTP-Spacing2* (cos RouteDir)))
                                                        (+ (cadr Pt2) (* *LEP-End-MTP-Spacing2* (sin RouteDir)))
                                                    )
                                                )
                                                (setq Ent3 (LEP:InsertPole Pt3 Rotation PoleType Status VClass))

                                                ;; ✅ ФИКС 2026-07-22 (по просьбе пользователя):
                                                ;; подпись МТП указывает на СЕРЕДИНУ между опорами
                                                ;; 2 и 3 (физически трансформатор МТП подвешен
                                                ;; МЕЖДУ ними), а не на саму опору 2 - опоры 2/3
                                                ;; сами по себе НЕ переехали, Pt2/Pt3 те же точки,
                                                ;; что и раньше, поменялась только точка, куда
                                                ;; указывает ВЫНОСКА подписи.
                                                (setq MtpMidPt
                                                    (list
                                                        (/ (+ (car Pt2) (car Pt3)) 2.0)
                                                        (/ (+ (cadr Pt2) (cadr Pt3)) 2.0)
                                                    )
                                                )
                                                ;; MtpLabel - выбранная мощность (2026-07-16), не
                                                ;; общий фиксированный *LEP-Label-MTP* - записывается
                                                ;; целиком как EQUIP, чтобы разные МТП по мощности не
                                                ;; слились в одну строку в ведомости (см. LEP-CONFIG.LSP,
                                                ;; *LEP-MTP-Types*, и LEP:GetEquipLabel в LEP-REPORT.LSP).
                                                ;; ⚠️ Подпись МТП висит на СЕРЕДИНЕ между опорами 2 и
                                                ;; 3, но LABELHANDLE пишем опоре 2 - той, к которой
                                                ;; она относится по смыслу (и на которую в ведомости
                                                ;; записан сам МТП). Значит удаление опоры 2 уберёт и
                                                ;; эту подпись - так и надо.
                                                (setq LabelEnt (LEP:CreatePoleLabel MtpMidPt PoleType Status MtpLabel *LEP-End-LabelAngle-MTP*))
                                                (LEP:AddEquipData Ent2 RouteID PoleType MtpLabel Status LabelEnt)

                                                (setq LabelEnt (LEP:CreatePoleLabel Pt3 PoleType Status *LEP-Label-SchU* *LEP-End-LabelAngle-SchU*))
                                                (LEP:AddEquipData Ent3 RouteID PoleType "SCHU" Status LabelEnt)

                                                (princ "\n[LEP-END] Установлен блок МТП (3 опоры: РЛК/МТП/ЩУ, подпись МТП - между 2-й и 3-й опорой).")
                                            )
                                        )
                                    )
                                )
                                (princ "\n[LEP-END] Точка не указана - отменено.")
                            )
                        )
                        (princ "\nМаршрут не выбран.")
                    )
                )
            )
        )
        (princ "\n[LEP-END] Отменено.")
    )

    (setvar "OSMODE" OldOs)

    (setq *error* OldError)
    (LEP:PrintFooter)
    (princ)
)


(princ "\nLEP-END v1.1 загружен (МТП 10 и 6 кВ, КТП блоком-символом, СТП текстом).")
(princ)
